Attribute VB_Name = "FlipForm"
Attribute VB_Base = "0{A60F1F48-DB5A-465E-9E07-C0AE9B3EBC01}{205CD0ED-5B2C-49B8-A28A-80175234058D}"
Attribute VB_GlobalNameSpace = False
Attribute VB_Creatable = False
Attribute VB_PredeclaredId = True
Attribute VB_Exposed = False
Attribute VB_TemplateDerived = False
Attribute VB_Customizable = False
Private Sub UserForm_Activate()
    ' 窗体显示后立即进入连续选孔循环
    ' 在 FlipForm 自身的事件调用栈中运行，消息泵不被阻断，三个按钮全程可响应
    Call DoSelectAndPlace
End Sub

Private Sub btnFlip_Click()
    If Not g_loopActive Then Exit Sub
    btnFlip.Enabled = False
    g_flipDir = Not g_flipDir
    If g_hasLastComp Then
        Call MoveLastFastener
        CATIA.StatusBar = "已重新定向  [翻转:" & IIf(g_flipDir, "是", "否") & "]  继续选孔，按 ESC 或点""退出""结束"
    End If
    btnFlip.Enabled = True
End Sub

Private Sub btnUndo_Click()
    If Not g_loopActive Then Exit Sub
    btnUndo.Enabled = False
    If g_historyCount > 0 Then Call UndoLastFastener
End Sub

Private Sub btnStop_Click()
    g_loopActive = False
    g_hasLastComp = False
    ' 异步发送 ESC（False=不等待），让 SelectElement2 在消息泵下一次调度时返回
    ' 不用 True（同步等待），避免在 UserForm_Activate 调用栈内死锁
    On Error Resume Next
    SendKeys "{ESC}", False
    On Error GoTo 0
End Sub

Private Sub UserForm_QueryClose(Cancel As Integer, CloseMode As Integer)
    ' 阻止默认关闭，走与 btnStop 相同的路径，由 ExitLoop 统一 Unload + MsgBox
    Cancel = True
    g_loopActive = False
    g_hasLastComp = False
    On Error Resume Next
    SendKeys "{ESC}", False
    On Error GoTo 0
End Sub

Private Sub UserForm_Click()

End Sub

Attribute VB_Name = "SwitchDocForm"
Attribute VB_Base = "0{F46D2CAA-EFE8-4F9F-9FAF-2FC3AC0FFE15}{BB70B130-2E4C-4224-8C7C-A530087C2DF3}"
Attribute VB_GlobalNameSpace = False
Attribute VB_Creatable = False
Attribute VB_PredeclaredId = True
Attribute VB_Exposed = False
Attribute VB_TemplateDerived = False
Attribute VB_Customizable = False
Private Sub btnContinue_Click()
    ' 调用主模块中的 ContinueSelectProduct。
    ' 若 ActiveDocument 不是 ProductDocument，该 Sub 会提示用户并直接返回，
    ' SwitchDocForm 保持打开，用户可再次切换后重试。
    Call ContinueSelectProduct
End Sub

Private Sub btnCancel_Click()
    Unload SwitchDocForm
End Sub

Attribute VB_Name = "SwitchToPartForm"
Attribute VB_Base = "0{6C31F6B0-F89A-4CAF-AA7D-1FFC81874F61}{7E843E89-4A7F-4BF2-956F-8B4C72BC3D6B}"
Attribute VB_GlobalNameSpace = False
Attribute VB_Creatable = False
Attribute VB_PredeclaredId = True
Attribute VB_Exposed = False
Attribute VB_TemplateDerived = False
Attribute VB_Customizable = False
Private Sub btnContinue_Click()
    ' 调用主模块中的 ContinueSelectFastener。
    ' 若 ActiveDocument 不是 PartDocument，该 Sub 会提示用户并直接返回，
    ' SwitchToPartForm 保持打开，用户可再次切换后重试。
    Call ContinueSelectFastener
End Sub

Private Sub btnCancel_Click()
    Unload SwitchToPartForm
End Sub

Attribute VB_Name = "模块1"
Option Explicit
' fastener_assembly - VBA 模块
' ── 调试开关：改为 False 关闭所有 [DEBUG] 弹窗（正式使用时设为 False）──────────
Public Const DEBUG_MODE As Boolean = False

' 翻转方向标志；由 FlipForm 按钮切换，跨次运行保持状态
Public g_flipDir As Boolean

' 紧固件参考几何（由 ContinueSelectFastener 读取一次，PlaceFastenerAtHole 使用）
Public g_faAxis(2)       ' 不声明 As Double，避免某些 CATIA 版本 GetAxis 无法写入
Public g_faAnchorPt(2)

' 最近一次孔的几何（选孔后更新，供翻转重装使用）
Public g_holeAxisX As Double, g_holeAxisY As Double, g_holeAxisZ As Double
Public g_holePtX   As Double, g_holePtY   As Double, g_holePtZ   As Double

' 最近装配件的信息（翻转重装时使用）
Public g_hasLastComp  As Boolean
Public g_lastProducts As Object
Public g_lastCompIdx  As Long

' 装配历史记录（供撤销使用）
Public g_assemblyHistory()
Public g_historyCount As Long

' 装配循环活动标志
Public g_loopActive As Boolean

' 装配循环共享状态
Public targetProduct   As Object
Public g_fastenerDoc   As Object
Public g_fastenerPN    As String
Public g_targetPN      As String
Public g_count         As Long

' ============================================================================
' CATMain
' ============================================================================
Public Sub CATMain()
    CATIA.StatusBar = "请切换到紧固件（CATPart）文档窗口，然后点击浮动面板上的""继续""按钮。"
    SwitchToPartForm.Show vbModeless
End Sub

' ============================================================================
' ContinueSelectFastener - 由 SwitchToPartForm.btnContinue_Click() 调用。
' ============================================================================
Public Sub ContinueSelectFastener()
    If TypeName(CATIA.ActiveDocument) <> "PartDocument" Then
        MsgBox "当前活动文档不是 CATPart。" & Chr(10) & _
               "请先切换到紧固件文档窗口，然后再点击""继续""。", _
               vbExclamation, "快速装配紧固件"
        Exit Sub
    End If

    Unload SwitchToPartForm

    Dim fastenerDoc As Object
    Set fastenerDoc = CATIA.ActiveDocument
    Set g_fastenerDoc = fastenerDoc
    g_fastenerPN = fastenerDoc.Product.PartNumber

    Dim sel As Object
    Set sel = fastenerDoc.Selection
    sel.Clear

    Dim fastEdgeFilter As Variant
    fastEdgeFilter = Array("MonoDim")
    Dim spaFastener As Object
    Set spaFastener = fastenerDoc.GetWorkbench("SPAWorkbench")

    Dim fastEdgeRef As Object
    Dim fastEdgeMeas As Object
    Dim faAxis(2)
    Dim faAnchorPt(2)
    Dim bFaGeomOK As Boolean
    Dim status As String

    Do
        status = sel.SelectElement2(fastEdgeFilter, _
            "请选择紧固件安装面上的圆或圆弧（确定轴向和定位点）[ESC 退出]", False)
        If status <> "Normal" Then Exit Sub

        Set fastEdgeRef = sel.Item(1).Reference
        Set fastEdgeMeas = spaFastener.GetMeasurable(fastEdgeRef)

        bFaGeomOK = TryGetAxis(fastEdgeMeas, faAxis) And TryGetCenter(fastEdgeMeas, faAnchorPt)
        If Not bFaGeomOK Then
            MsgBox "无法从所选元素获取轴向和圆心。" & Chr(10) & _
                   "请选择一个圆或一段圆弧（而非直线或曲线）。", _
                   vbExclamation, "快速装配紧固件"
            sel.Clear
        End If
    Loop While Not bFaGeomOK

    sel.Clear

    Dim faLen As Double
    faLen = Sqr(faAxis(0) * faAxis(0) + faAxis(1) * faAxis(1) + faAxis(2) * faAxis(2))
    If faLen > 0.000000000001 Then
        g_faAxis(0) = faAxis(0) / faLen: g_faAxis(1) = faAxis(1) / faLen: g_faAxis(2) = faAxis(2) / faLen
    Else
        g_faAxis(0) = faAxis(0): g_faAxis(1) = faAxis(1): g_faAxis(2) = faAxis(2)
    End If
    g_faAnchorPt(0) = faAnchorPt(0): g_faAnchorPt(1) = faAnchorPt(1): g_faAnchorPt(2) = faAnchorPt(2)

    If DEBUG_MODE Then
        MsgBox "[DEBUG] 紧固件参考几何" & Chr(10) & _
               "faAxis    = (" & Round(g_faAxis(0), 4) & ", " & Round(g_faAxis(1), 4) & ", " & Round(g_faAxis(2), 4) & ")" & Chr(10) & _
               "faAnchorPt= (" & Round(g_faAnchorPt(0), 4) & ", " & Round(g_faAnchorPt(1), 4) & ", " & Round(g_faAnchorPt(2), 4) & ")", _
               vbInformation, "快速装配紧固件 [DEBUG]"
    End If

    CATIA.StatusBar = "请切换到目标产品（CATProduct）文档窗口，然后点击浮动面板上的""继续""按钮。"
    SwitchDocForm.Show vbModeless
End Sub

' ============================================================================
' ContinueSelectProduct - 由 SwitchDocForm.btnContinue_Click() 调用。
' 只做"选目标产品"这一步，完成后显示 FlipForm 并立即返回。
' 装配循环由用户点击 FlipForm.btnStart 逐孔触发（DoSelectAndPlace）。
' ============================================================================
Public Sub ContinueSelectProduct()
    If TypeName(CATIA.ActiveDocument) <> "ProductDocument" Then
        MsgBox "当前活动文档不是 CATProduct。" & Chr(10) & _
               "请先切换到目标产品文档窗口，然后再点击""继续""。", _
               vbExclamation, "快速装配紧固件"
        Exit Sub
    End If

    Unload SwitchDocForm

    Dim rootDoc As Object
    Set rootDoc = CATIA.ActiveDocument
    Dim sel As Object
    Set sel = rootDoc.Selection
    sel.Clear

    ' 选目标产品/部件
    Dim prodFilter As Variant
    prodFilter = Array("Product")
    Dim status As String
    status = sel.SelectElement2(prodFilter, _
        "在产品结构树中选择紧固件要装入的产品/部件", False)
    If status <> "Normal" Then
        MsgBox "已取消选择。", vbInformation, "快速装配紧固件"
        Exit Sub
    End If

    Set targetProduct = Nothing
    On Error Resume Next
    Set targetProduct = sel.Item(1).Value
    On Error GoTo 0

    If targetProduct Is Nothing Or TypeName(targetProduct) <> "Product" Then
        MsgBox "所选对象不是产品或部件。" & Chr(10) & _
               "请在产品结构树中选择一个产品（Product）或部件。", _
               vbExclamation, "快速装配紧固件"
        sel.Clear
        Exit Sub
    End If

    g_targetPN = targetProduct.PartNumber
    sel.Clear

    ' 初始化装配状态
    g_count = 0
    g_hasLastComp = False
    g_loopActive = True
    g_historyCount = 0
    ReDim g_assemblyHistory(0 To 99, 0 To 7)

    ' 显示装配控制面板；UserForm_Activate 会自动调用 DoSelectAndPlace 开始循环
    FlipForm.Show vbModeless
    FlipForm.btnFlip.Enabled = False
    FlipForm.btnUndo.Enabled = False
    CATIA.StatusBar = "目标产品已选定：" & g_targetPN & "  请选择孔位"
End Sub

' ============================================================================
' DoSelectAndPlace - 由 FlipForm.UserForm_Activate 触发，在 FlipForm 的事件
' 调用栈中执行连续"选孔 → 装配"循环，直到用户按 ESC 或点"退出"为止。
' 因为整个循环在 FlipForm 自身的事件里运行，SelectElement2 等待期间
' CATIA 消息泵正常运转，"翻转"/"撤销"/"退出"全程可响应。
' ============================================================================
Public Sub DoSelectAndPlace()
    If Not g_loopActive Then Exit Sub

    Dim sel As Object
    Dim spaAssembly As Object
    Dim firstFilter As Variant
    Dim holeFilter As Variant
    Dim holeAxis(2)
    Dim holePt(2)
    Dim bHoleGeomOK As Boolean
    Dim status As String
    Dim firstRef As Object
    Dim firstLeafProd As Object
    Dim firstMeas As Object
    Dim holeAxisLen As Double
    Dim ptCoord(2)
    Dim ptAxis(2)
    Dim lineRef As Object
    Dim lineLeafProd As Object
    Dim lineMeas As Object
    Dim lineDir(2)
    Dim lineDirLen As Double
    Dim zeroOff(2)

    firstFilter = Array("MonoDim", "Vertex")
    holeFilter = Array("MonoDim")

    Do While g_loopActive

        Set sel = CATIA.ActiveDocument.Selection
        sel.Clear
        Set spaAssembly = CATIA.ActiveDocument.GetWorkbench("SPAWorkbench")
        bHoleGeomOK = False

        ' ── 选孔位元素（圆形边 或 顶点） ──────────────────────────────────
        status = sel.SelectElement2(firstFilter, _
            "选择孔的圆形边（圆弧模式）或安装锚点顶点（点+线模式） [" & g_fastenerPN & " -> " & g_targetPN & _
            "  已装配:" & g_count & "]  按 ESC 或点""退出""结束", False)

        If status <> "Normal" Or Not g_loopActive Then GoTo ExitLoop

        Set firstRef = sel.Item(1).Reference
        Set firstLeafProd = sel.Item(1).LeafProduct

        If Not TryGetMeasurable(spaAssembly, firstRef, firstMeas) Then
            MsgBox "无法测量所选元素，请重新选择。", vbExclamation, "快速装配紧固件"
            sel.Clear
            GoTo NextRound
        End If

        ' ── 圆弧模式 vs 点+线模式 ───────────────────────────────────────
        If TryGetAxis(firstMeas, holeAxis) And TryGetCenter(firstMeas, holePt) Then
            ' 圆弧模式
            holeAxisLen = Sqr(holeAxis(0) * holeAxis(0) + holeAxis(1) * holeAxis(1) + holeAxis(2) * holeAxis(2))
            If holeAxisLen > 0.000000000001 Then
                holeAxis(0) = holeAxis(0) / holeAxisLen
                holeAxis(1) = holeAxis(1) / holeAxisLen
                holeAxis(2) = holeAxis(2) / holeAxisLen
            End If
            Call TransformToRoot(firstLeafProd, holePt, holeAxis)
            Call TransformToTarget(holePt, holeAxis)
            bHoleGeomOK = True
        ElseIf TryGetPoint(firstMeas, ptCoord) Then
            ' 点+线模式：顶点 + 轴线
            ptAxis(0) = 0: ptAxis(1) = 0: ptAxis(2) = 0
            Call TransformToRoot(firstLeafProd, ptCoord, ptAxis)

            sel.Clear
            status = sel.SelectElement2(holeFilter, _
                "【点+线模式】选择轴线方向（直线或轴线）", False)
            If status <> "Normal" Or Not g_loopActive Then GoTo ExitLoop

            Set lineRef = sel.Item(1).Reference
            Set lineLeafProd = sel.Item(1).LeafProduct

            If TryGetMeasurable(spaAssembly, lineRef, lineMeas) And TryGetDirection(lineMeas, lineDir) Then
                lineDirLen = Sqr(lineDir(0) * lineDir(0) + lineDir(1) * lineDir(1) + lineDir(2) * lineDir(2))
                If lineDirLen > 0.000000000001 Then
                    lineDir(0) = lineDir(0) / lineDirLen
                    lineDir(1) = lineDir(1) / lineDirLen
                    lineDir(2) = lineDir(2) / lineDirLen
                End If
                zeroOff(0) = 0: zeroOff(1) = 0: zeroOff(2) = 0
                Call TransformToRoot(lineLeafProd, zeroOff, lineDir)
                Call TransformToTarget(ptCoord, lineDir)
                holePt(0) = ptCoord(0): holePt(1) = ptCoord(1): holePt(2) = ptCoord(2)
                holeAxis(0) = lineDir(0): holeAxis(1) = lineDir(1): holeAxis(2) = lineDir(2)
                bHoleGeomOK = True
            Else
                MsgBox "无法获取所选直线的方向，请选择一条直线或直线型边。", _
                       vbExclamation, "快速装配紧固件"
            End If
        Else
            MsgBox "无法识别所选元素。" & Chr(10) & _
                   "请选择孔入口处的圆形边，或安装锚点（顶点）。", _
                   vbExclamation, "快速装配紧固件"
        End If

        sel.Clear

        If bHoleGeomOK Then
            g_holeAxisX = holeAxis(0): g_holeAxisY = holeAxis(1): g_holeAxisZ = holeAxis(2)
            g_holePtX = holePt(0):     g_holePtY = holePt(1):     g_holePtZ = holePt(2)

            If DEBUG_MODE Then
                MsgBox "[DEBUG] 孔的几何（targetProduct 局部坐标系）" & Chr(10) & _
                       "holeAxis = (" & Round(holeAxis(0), 4) & ", " & Round(holeAxis(1), 4) & ", " & Round(holeAxis(2), 4) & ")" & Chr(10) & _
                       "holePt   = (" & Round(holePt(0), 4) & ", " & Round(holePt(1), 4) & ", " & Round(holePt(2), 4) & ")", _
                       vbInformation, "快速装配紧固件 [DEBUG]"
            End If

            Call PlaceFastenerAtHole

            CATIA.StatusBar = "已装配 " & g_count & " 个 " & g_fastenerPN & " -> " & g_targetPN & _
                              "  [翻转:" & IIf(g_flipDir, "是", "否") & "]  继续选孔，按 ESC 或点""退出""结束"
        End If

NextRound:
    Loop

ExitLoop:
    g_loopActive = False
    g_hasLastComp = False
    sel.Clear
    ' 窗体可能已被用户关闭，加保护避免重复 Unload 报错
    On Error Resume Next
    Unload FlipForm
    On Error GoTo 0
    MsgBox "装配完成！" & Chr(10) & _
           "共装配 " & g_count & " 个 " & g_fastenerPN & " 到 " & g_targetPN & "。", _
           vbInformation, "快速装配紧固件"
End Sub

' ============================================================================
' TransformToRoot：将点 pt 和方向向量 dir 从 leafProd 局部坐标系
' 逐层正向变换到根产品坐标系（ProductDocument 层）。
' 方向向量只做旋转，不做平移。
' ============================================================================
Private Sub TransformToRoot(ByVal leafProd As Object, ByRef pt(), ByRef dir())
    Dim curProd As Object
    Set curProd = leafProd
    Dim m(11)
    Dim parentColl As Object
    Dim tx As Double, ty As Double, tz As Double

    Do
        Set parentColl = curProd.Parent
        If TypeName(parentColl) = "ProductDocument" Then Exit Do
        curProd.Position.GetComponents m
        ' 点：旋转 + 平移
        tx = m(0) * pt(0) + m(3) * pt(1) + m(6) * pt(2) + m(9)
        ty = m(1) * pt(0) + m(4) * pt(1) + m(7) * pt(2) + m(10)
        tz = m(2) * pt(0) + m(5) * pt(1) + m(8) * pt(2) + m(11)
        pt(0) = tx: pt(1) = ty: pt(2) = tz
        ' 方向：只旋转
        tx = m(0) * dir(0) + m(3) * dir(1) + m(6) * dir(2)
        ty = m(1) * dir(0) + m(4) * dir(1) + m(7) * dir(2)
        tz = m(2) * dir(0) + m(5) * dir(1) + m(8) * dir(2)
        dir(0) = tx: dir(1) = ty: dir(2) = tz
        Set curProd = parentColl.Parent
    Loop
End Sub

' ============================================================================
' TransformToTarget：将根坐标系中的点 pt 和方向 dir 逆变换到
' targetProduct 局部坐标系。
' ============================================================================
Private Sub TransformToTarget(ByRef pt(), ByRef dir())
    ' 收集 targetProduct → 根 的变换链
    Dim chain(49, 11)
    Dim depth As Integer
    depth = 0
    Dim curProd As Object
    Set curProd = targetProduct
    Dim m(11)
    Dim parentColl As Object
    Dim kk As Integer

    Do
        Set parentColl = curProd.Parent
        If TypeName(parentColl) = "ProductDocument" Then Exit Do
        curProd.Position.GetComponents m
        For kk = 0 To 11: chain(depth, kk) = m(kk): Next kk
        depth = depth + 1
        Set curProd = parentColl.Parent
    Loop

    ' 从根向下（逆序）施加逆变换：local = R^T * (parent - T)
    Dim ii As Integer
    Dim off0 As Double, off1 As Double, off2 As Double
    Dim ax As Double, ay As Double, az As Double

    For ii = depth - 1 To 0 Step -1
        off0 = pt(0) - chain(ii, 9)
        off1 = pt(1) - chain(ii, 10)
        off2 = pt(2) - chain(ii, 11)
        pt(0) = chain(ii, 0) * off0 + chain(ii, 1) * off1 + chain(ii, 2) * off2
        pt(1) = chain(ii, 3) * off0 + chain(ii, 4) * off1 + chain(ii, 5) * off2
        pt(2) = chain(ii, 6) * off0 + chain(ii, 7) * off1 + chain(ii, 8) * off2
        ax = chain(ii, 0) * dir(0) + chain(ii, 1) * dir(1) + chain(ii, 2) * dir(2)
        ay = chain(ii, 3) * dir(0) + chain(ii, 4) * dir(1) + chain(ii, 5) * dir(2)
        az = chain(ii, 6) * dir(0) + chain(ii, 7) * dir(1) + chain(ii, 8) * dir(2)
        dir(0) = ax: dir(1) = ay: dir(2) = az
    Next ii
End Sub

' ============================================================================
' PlaceFastenerAtHole
' ============================================================================
Public Sub PlaceFastenerAtHole()
    Dim insertionDir(2) As Double
    If g_flipDir Then
        insertionDir(0) = -g_holeAxisX: insertionDir(1) = -g_holeAxisY: insertionDir(2) = -g_holeAxisZ
    Else
        insertionDir(0) = g_holeAxisX: insertionDir(1) = g_holeAxisY: insertionDir(2) = g_holeAxisZ
    End If

    Dim holeCenterLocal(2) As Double
    holeCenterLocal(0) = g_holePtX: holeCenterLocal(1) = g_holePtY: holeCenterLocal(2) = g_holePtZ

    Dim f1x(2) As Double, f1y(2) As Double, f1z(2) As Double
    f1z(0) = g_faAxis(0): f1z(1) = g_faAxis(1): f1z(2) = g_faAxis(2)
    Call BuildFrame(f1z, f1x, f1y)

    Dim f2x(2) As Double, f2y(2) As Double, f2z(2) As Double
    f2z(0) = insertionDir(0): f2z(1) = insertionDir(1): f2z(2) = insertionDir(2)
    Call BuildFrame(f2z, f2x, f2y)

    Dim R(2, 2) As Double
    Dim ri As Integer, rj As Integer
    For ri = 0 To 2
        For rj = 0 To 2
            R(ri, rj) = FrameCol(ri, 0, f2x, f2y, f2z) * FrameCol(rj, 0, f1x, f1y, f1z) _
                      + FrameCol(ri, 1, f2x, f2y, f2z) * FrameCol(rj, 1, f1x, f1y, f1z) _
                      + FrameCol(ri, 2, f2x, f2y, f2z) * FrameCol(rj, 2, f1x, f1y, f1z)
        Next rj
    Next ri

    Dim rotatedAnchor(2) As Double
    rotatedAnchor(0) = R(0, 0) * g_faAnchorPt(0) + R(0, 1) * g_faAnchorPt(1) + R(0, 2) * g_faAnchorPt(2)
    rotatedAnchor(1) = R(1, 0) * g_faAnchorPt(0) + R(1, 1) * g_faAnchorPt(1) + R(1, 2) * g_faAnchorPt(2)
    rotatedAnchor(2) = R(2, 0) * g_faAnchorPt(0) + R(2, 1) * g_faAnchorPt(1) + R(2, 2) * g_faAnchorPt(2)

    Dim translation(2) As Double
    translation(0) = holeCenterLocal(0) - rotatedAnchor(0)
    translation(1) = holeCenterLocal(1) - rotatedAnchor(1)
    translation(2) = holeCenterLocal(2) - rotatedAnchor(2)

    Dim products As Object
    Set products = targetProduct.products
    products.AddComponent g_fastenerDoc.Product

    Dim newComp As Object
    Set newComp = products.Item(products.Count)

    Dim moveMatrix(11)
    moveMatrix(0) = R(0, 0): moveMatrix(1) = R(1, 0): moveMatrix(2) = R(2, 0)
    moveMatrix(3) = R(0, 1): moveMatrix(4) = R(1, 1): moveMatrix(5) = R(2, 1)
    moveMatrix(6) = R(0, 2): moveMatrix(7) = R(1, 2): moveMatrix(8) = R(2, 2)
    moveMatrix(9) = translation(0)
    moveMatrix(10) = translation(1)
    moveMatrix(11) = translation(2)

    If DEBUG_MODE Then
        MsgBox "[DEBUG] 最终定位矩阵（targetProduct 坐标系）" & Chr(10) & _
               "R X轴 = (" & Round(R(0, 0), 4) & ", " & Round(R(1, 0), 4) & ", " & Round(R(2, 0), 4) & ")" & Chr(10) & _
               "R Y轴 = (" & Round(R(0, 1), 4) & ", " & Round(R(1, 1), 4) & ", " & Round(R(2, 1), 4) & ")" & Chr(10) & _
               "R Z轴 = (" & Round(R(0, 2), 4) & ", " & Round(R(1, 2), 4) & ", " & Round(R(2, 2), 4) & ")" & Chr(10) & _
               "平移  = (" & Round(translation(0), 4) & ", " & Round(translation(1), 4) & ", " & Round(translation(2), 4) & ")", _
               vbInformation, "快速装配紧固件 [DEBUG]"
    End If

    newComp.Position.SetComponents moveMatrix

    Set g_lastProducts = products
    g_lastCompIdx = products.Count
    g_count = g_count + 1
    g_hasLastComp = True
    FlipForm.btnFlip.Enabled = True

    If g_historyCount < 100 Then
        Set g_assemblyHistory(g_historyCount, 0) = products
        g_assemblyHistory(g_historyCount, 1) = products.Count
        g_assemblyHistory(g_historyCount, 2) = g_holeAxisX
        g_assemblyHistory(g_historyCount, 3) = g_holeAxisY
        g_assemblyHistory(g_historyCount, 4) = g_holeAxisZ
        g_assemblyHistory(g_historyCount, 5) = g_holePtX
        g_assemblyHistory(g_historyCount, 6) = g_holePtY
        g_assemblyHistory(g_historyCount, 7) = g_holePtZ
        g_historyCount = g_historyCount + 1
        FlipForm.btnUndo.Enabled = True
    End If
End Sub

' ============================================================================
' MoveLastFastener
' ============================================================================
Public Sub MoveLastFastener()
    Dim lastComp As Object
    Set lastComp = g_lastProducts.Item(g_lastCompIdx)

    Dim insertionDir(2) As Double
    If g_flipDir Then
        insertionDir(0) = -g_holeAxisX: insertionDir(1) = -g_holeAxisY: insertionDir(2) = -g_holeAxisZ
    Else
        insertionDir(0) = g_holeAxisX: insertionDir(1) = g_holeAxisY: insertionDir(2) = g_holeAxisZ
    End If

    Dim holeCenterLocal(2) As Double
    holeCenterLocal(0) = g_holePtX: holeCenterLocal(1) = g_holePtY: holeCenterLocal(2) = g_holePtZ

    Dim f1x(2) As Double, f1y(2) As Double, f1z(2) As Double
    f1z(0) = g_faAxis(0): f1z(1) = g_faAxis(1): f1z(2) = g_faAxis(2)
    Call BuildFrame(f1z, f1x, f1y)

    Dim f2x(2) As Double, f2y(2) As Double, f2z(2) As Double
    f2z(0) = insertionDir(0): f2z(1) = insertionDir(1): f2z(2) = insertionDir(2)
    Call BuildFrame(f2z, f2x, f2y)

    Dim R(2, 2) As Double
    Dim ri As Integer, rj As Integer
    For ri = 0 To 2
        For rj = 0 To 2
            R(ri, rj) = FrameCol(ri, 0, f2x, f2y, f2z) * FrameCol(rj, 0, f1x, f1y, f1z) _
                      + FrameCol(ri, 1, f2x, f2y, f2z) * FrameCol(rj, 1, f1x, f1y, f1z) _
                      + FrameCol(ri, 2, f2x, f2y, f2z) * FrameCol(rj, 2, f1x, f1y, f1z)
        Next rj
    Next ri

    Dim rotatedAnchor(2) As Double
    rotatedAnchor(0) = R(0, 0) * g_faAnchorPt(0) + R(0, 1) * g_faAnchorPt(1) + R(0, 2) * g_faAnchorPt(2)
    rotatedAnchor(1) = R(1, 0) * g_faAnchorPt(0) + R(1, 1) * g_faAnchorPt(1) + R(1, 2) * g_faAnchorPt(2)
    rotatedAnchor(2) = R(2, 0) * g_faAnchorPt(0) + R(2, 1) * g_faAnchorPt(1) + R(2, 2) * g_faAnchorPt(2)

    Dim translation(2) As Double
    translation(0) = holeCenterLocal(0) - rotatedAnchor(0)
    translation(1) = holeCenterLocal(1) - rotatedAnchor(1)
    translation(2) = holeCenterLocal(2) - rotatedAnchor(2)

    Dim moveMatrix(11)
    moveMatrix(0) = R(0, 0): moveMatrix(1) = R(1, 0): moveMatrix(2) = R(2, 0)
    moveMatrix(3) = R(0, 1): moveMatrix(4) = R(1, 1): moveMatrix(5) = R(2, 1)
    moveMatrix(6) = R(0, 2): moveMatrix(7) = R(1, 2): moveMatrix(8) = R(2, 2)
    moveMatrix(9) = translation(0)
    moveMatrix(10) = translation(1)
    moveMatrix(11) = translation(2)

    lastComp.Position.SetComponents moveMatrix
End Sub

' ============================================================================
' UndoLastFastener
' ============================================================================
Public Sub UndoLastFastener()
    If g_historyCount = 0 Then Exit Sub

    Dim lastIdx As Long
    lastIdx = g_historyCount - 1
    Dim products As Object
    Set products = g_assemblyHistory(lastIdx, 0)
    Dim compIdx As Long
    compIdx = CLng(g_assemblyHistory(lastIdx, 1))

    On Error Resume Next
    products.Remove compIdx
    On Error GoTo 0

    Set g_assemblyHistory(lastIdx, 0) = Nothing
    g_assemblyHistory(lastIdx, 1) = 0
    g_historyCount = g_historyCount - 1
    g_count = g_count - 1

    FlipForm.btnUndo.Enabled = (g_historyCount > 0)
    g_hasLastComp = False
    FlipForm.btnFlip.Enabled = False

    CATIA.StatusBar = "已撤销上一个紧固件。当前已装配: " & g_count & " 个 " & g_fastenerPN
End Sub

' ============================================================================
' BuildFrame
' ============================================================================
Private Sub BuildFrame(ByRef inZ() As Double, ByRef outX() As Double, ByRef outY() As Double)
    Dim zLen As Double
    zLen = Sqr(inZ(0) * inZ(0) + inZ(1) * inZ(1) + inZ(2) * inZ(2))
    If zLen < 0.000000000001 Then
        outX(0) = 1: outX(1) = 0: outX(2) = 0
        outY(0) = 0: outY(1) = 1: outY(2) = 0
        Exit Sub
    End If
    Dim nz(2) As Double
    nz(0) = inZ(0) / zLen: nz(1) = inZ(1) / zLen: nz(2) = inZ(2) / zLen

    Dim refV(2) As Double
    If Abs(nz(0)) < 0.9 Then
        refV(0) = 1: refV(1) = 0: refV(2) = 0
    Else
        refV(0) = 0: refV(1) = 1: refV(2) = 0
    End If

    outX(0) = nz(1) * refV(2) - nz(2) * refV(1)
    outX(1) = nz(2) * refV(0) - nz(0) * refV(2)
    outX(2) = nz(0) * refV(1) - nz(1) * refV(0)
    Dim xLen As Double
    xLen = Sqr(outX(0) * outX(0) + outX(1) * outX(1) + outX(2) * outX(2))
    If xLen < 0.000000000001 Then
        outX(0) = 1: outX(1) = 0: outX(2) = 0
        outY(0) = 0: outY(1) = 1: outY(2) = 0
        Exit Sub
    End If
    outX(0) = outX(0) / xLen: outX(1) = outX(1) / xLen: outX(2) = outX(2) / xLen
    outY(0) = nz(1) * outX(2) - nz(2) * outX(1)
    outY(1) = nz(2) * outX(0) - nz(0) * outX(2)
    outY(2) = nz(0) * outX(1) - nz(1) * outX(0)
End Sub

' ============================================================================
' FrameCol
' ============================================================================
Private Function FrameCol(ByVal row As Integer, ByVal col As Integer, _
                          ByRef vx() As Double, ByRef vy() As Double, _
                          ByRef vz() As Double) As Double
    Select Case col
        Case 0: FrameCol = vx(row)
        Case 1: FrameCol = vy(row)
        Case 2: FrameCol = vz(row)
    End Select
End Function

' ============================================================================
' TryGet* 辅助函数（独立错误域）
' ============================================================================
Private Function TryGetAxis(meas As Object, axArr) As Boolean
    On Error Resume Next: Err.Clear
    meas.GetAxis axArr
    TryGetAxis = (Err.Number = 0)
End Function

Private Function TryGetDirection(meas As Object, dirArr) As Boolean
    On Error Resume Next: Err.Clear
    meas.GetDirection dirArr
    TryGetDirection = (Err.Number = 0)
End Function

Private Function TryGetCenter(meas As Object, ptArr) As Boolean
    On Error Resume Next: Err.Clear
    meas.GetCenter ptArr
    TryGetCenter = (Err.Number = 0)
End Function

Private Function TryGetPoint(meas As Object, ptArr) As Boolean
    On Error Resume Next: Err.Clear
    meas.GetPoint ptArr
    TryGetPoint = (Err.Number = 0)
End Function

Private Function TryGetMeasurable(spa As Object, ref As Object, _
                                  ByRef measOut As Object) As Boolean
    On Error Resume Next: Err.Clear
    Set measOut = spa.GetMeasurable(ref)
    TryGetMeasurable = (Err.Number = 0 And Not measOut Is Nothing)
End Function
