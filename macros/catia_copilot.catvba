Attribute VB_Name = "FlipForm_FA"
Attribute VB_Base = "0{9B6C8A5C-C213-4C94-87BA-15878872401C}{99283A7C-07C2-4ABB-8C53-5D9D67066C7B}"
Attribute VB_GlobalNameSpace = False
Attribute VB_Creatable = False
Attribute VB_PredeclaredId = True
Attribute VB_Exposed = False
Attribute VB_TemplateDerived = False
Attribute VB_Customizable = False
Private Sub UserForm_Activate()
    ' 窗体显示后立即进入连续选孔循环
    ' 在 FlipForm_FA 自身的事件调用栈中运行，消息泵不被阻断，三个按钮全程可响应
    Call DoSelectAndPlace_FA
    ' DoSelectAndPlace_FA 返回时循环已退出，在此安全执行收尾
    Unload Me
    MsgBox "装配完成！" & Chr(10) & _
           "共装配 " & g_count_FA & " 个 " & g_fastenerPN & " 到 " & g_targetPN_FA & "。", _
           vbInformation, "快速装配紧固件"
End Sub

Private Sub btnFlip_Click()
    If Not g_loopActive_FA Then Exit Sub
    btnFlip.Enabled = False
    g_flipDir_FA = Not g_flipDir_FA
    If g_hasLastComp_FA Then
        Call MoveLastFastener
        CATIA.StatusBar = "已重新定向  [翻转:" & IIf(g_flipDir_FA, "是", "否") & "]  继续选孔，按 ESC 或点""退出""结束"
    End If
    btnFlip.Enabled = True
End Sub

Private Sub btnUndo_Click()
    If Not g_loopActive_FA Then Exit Sub
    btnUndo.Enabled = False
    If g_historyCount_FA > 0 Then Call UndoLastFastener
End Sub

Private Sub btnStop_Click()
    g_loopActive_FA = False
    g_hasLastComp_FA = False
    On Error Resume Next
    SendKeys "{ESC}", True
    DoEvents
    On Error GoTo 0
End Sub

Private Sub UserForm_QueryClose(Cancel As Integer, CloseMode As Integer)
    If g_loopActive_FA Then
        Cancel = True
        g_loopActive_FA = False
        g_hasLastComp_FA = False
        On Error Resume Next
        SendKeys "{ESC}", True
        DoEvents
        On Error GoTo 0
    End If
End Sub

Private Sub UserForm_Click()

End Sub

Attribute VB_Name = "FlipForm_NP"
Attribute VB_Base = "0{633A2C71-932F-4D10-985B-765272C637B5}{4F8874EF-7CBE-45A4-89B7-CA07D08D6DA4}"
Attribute VB_GlobalNameSpace = False
Attribute VB_Creatable = False
Attribute VB_PredeclaredId = True
Attribute VB_Exposed = False
Attribute VB_TemplateDerived = False
Attribute VB_Customizable = False
Private Sub UserForm_Activate()
    ' 窗体显示后立即进入连续选孔循环
    ' 在 FlipForm_NP 自身的事件调用栈中运行，消息泵不被阻断，四个按钮全程可响应
    Call DoSelectAndPlace_NP
    ' DoSelectAndPlace_NP 返回时循环已退出，在此安全执行收尾
    Unload Me
    MsgBox "装配完成！" & Chr(10) & _
           "共装配 " & g_count_NP & " 个 " & g_nutPlatePN & " 到 " & g_targetPN_NP & "。", _
           vbInformation, "快速装配托板螺母"
End Sub

Private Sub btnFlip_Click()
    If Not g_loopActive_NP Then Exit Sub
    btnFlip.Enabled = False
    g_flipDir_NP = Not g_flipDir_NP
    If g_hasLastComp_NP Then
        Call MoveLastNutPlate
        CATIA.StatusBar = "已重新定向（翻转）  [翻转:" & IIf(g_flipDir_NP, "是", "否") & _
                          "  对调:" & IIf(g_swapHoles_NP, "是", "否") & "]  继续选孔，按 ESC 或点""退出""结束"
    End If
    btnFlip.Enabled = True
End Sub

Private Sub btnSwap_Click()
    If Not g_loopActive_NP Then Exit Sub
    btnSwap.Enabled = False
    g_swapHoles_NP = Not g_swapHoles_NP
    If g_hasLastComp_NP Then
        Call MoveLastNutPlate
        CATIA.StatusBar = "已重新定向（对调）  [翻转:" & IIf(g_flipDir_NP, "是", "否") & _
                          "  对调:" & IIf(g_swapHoles_NP, "是", "否") & "]  继续选孔，按 ESC 或点""退出""结束"
    End If
    btnSwap.Enabled = True
End Sub

Private Sub btnUndo_Click()
    If Not g_loopActive_NP Then Exit Sub
    btnUndo.Enabled = False
    If g_historyCount_NP > 0 Then Call UndoLastNutPlate
End Sub

Private Sub btnStop_Click()
    g_loopActive_NP = False
    g_hasLastComp_NP = False
    On Error Resume Next
    SendKeys "{ESC}", True
    DoEvents
    On Error GoTo 0
End Sub

Private Sub UserForm_QueryClose(Cancel As Integer, CloseMode As Integer)
    If g_loopActive_NP Then
        Cancel = True
        g_loopActive_NP = False
        g_hasLastComp_NP = False
        On Error Resume Next
        SendKeys "{ESC}", True
        DoEvents
        On Error GoTo 0
    End If
End Sub

Private Sub UserForm_Click()

End Sub

Attribute VB_Name = "SwitchDocForm_FA"
Attribute VB_Base = "0{3E483162-28F3-4FCA-8E20-6D96BE275980}{12223AD7-2B49-4856-9DBC-3381752AA1B7}"
Attribute VB_GlobalNameSpace = False
Attribute VB_Creatable = False
Attribute VB_PredeclaredId = True
Attribute VB_Exposed = False
Attribute VB_TemplateDerived = False
Attribute VB_Customizable = False
Private Sub btnContinue_Click()
    Call ContinueSelectProduct_FA
End Sub

Private Sub btnCancel_Click()
    Unload SwitchDocForm_FA
End Sub

Private Sub UserForm_Click()

End Sub

Attribute VB_Name = "SwitchDocForm_NP"
Attribute VB_Base = "0{CAF15BAF-2CC7-4DE5-A855-94B61FBACED3}{158B0695-455E-4967-9EFB-D2FEAC814D1D}"
Attribute VB_GlobalNameSpace = False
Attribute VB_Creatable = False
Attribute VB_PredeclaredId = True
Attribute VB_Exposed = False
Attribute VB_TemplateDerived = False
Attribute VB_Customizable = False
Private Sub btnContinue_Click()
    Call ContinueSelectProduct_NP
End Sub

Private Sub btnCancel_Click()
    Unload SwitchDocForm_NP
End Sub

Private Sub UserForm_Click()

End Sub

Attribute VB_Name = "SwitchToPartForm_FA"
Attribute VB_Base = "0{57E81165-553F-4365-8AD4-9E6ABAE11182}{E4F5B309-2F05-412D-84A3-22A96D0BA000}"
Attribute VB_GlobalNameSpace = False
Attribute VB_Creatable = False
Attribute VB_PredeclaredId = True
Attribute VB_Exposed = False
Attribute VB_TemplateDerived = False
Attribute VB_Customizable = False
Private Sub btnContinue_Click()
    Call ContinueSelectFastener
End Sub

Private Sub btnCancel_Click()
    Unload SwitchToPartForm_FA
End Sub

Private Sub UserForm_Click()

End Sub

Attribute VB_Name = "SwitchToPartForm_NP"
Attribute VB_Base = "0{65D294F2-A60B-454E-8AAB-0DDFCADE2632}{CF7431E6-2429-4001-994B-ADAC2282EA79}"
Attribute VB_GlobalNameSpace = False
Attribute VB_Creatable = False
Attribute VB_PredeclaredId = True
Attribute VB_Exposed = False
Attribute VB_TemplateDerived = False
Attribute VB_Customizable = False
Private Sub btnContinue_Click()
    Call ContinueSelectNutPlate
End Sub

Private Sub btnCancel_Click()
    Unload SwitchToPartForm_NP
End Sub

Private Sub UserForm_Click()

End Sub

Attribute VB_Name = "fastener_assembly"
Option Explicit
' fastener_assembly - VBA 模块
' ── 调试开关：改为 False 关闭所有 [DEBUG] 弹窗（正式使用时设为 False）──────────
Public Const DEBUG_MODE_FA As Boolean = False

' 翻转方向标志；由 FlipForm_FA 按钮切换，跨次运行保持状态
Public g_flipDir_FA As Boolean

' 紧固件参考几何（由 ContinueSelectFastener 读取一次，PlaceFastenerAtHole 使用）
Public g_faAxis(2)       ' 不声明 As Double，避免某些 CATIA 版本 GetAxis 无法写入
Public g_faAnchorPt(2)

' 最近一次孔的几何（选孔后更新，供翻转重装使用）
Public g_holeAxisX As Double, g_holeAxisY As Double, g_holeAxisZ As Double
Public g_holePtX_FA   As Double, g_holePtY_FA   As Double, g_holePtZ_FA   As Double

' 最近装配件的信息（翻转重装时使用）
Public g_hasLastComp_FA  As Boolean
Public g_lastProducts_FA As Object
Public g_lastCompIdx_FA  As Long

' 装配历史记录（供撤销使用）
Public g_assemblyHistory_FA()
Public g_historyCount_FA As Long

' 装配循环活动标志
Public g_loopActive_FA As Boolean

' 装配循环共享状态
Public targetProduct_FA   As Object
Public g_fastenerDoc   As Object
Public g_fastenerPN    As String
Public g_targetPN_FA      As String
Public g_count_FA         As Long

' ============================================================================
' CATMain
' ============================================================================
Public Sub CATMain()
    CATIA.StatusBar = "请切换到紧固件（CATPart）文档窗口，然后点击浮动面板上的""继续""按钮。"
    SwitchToPartForm_FA.Show vbModeless
End Sub

' ============================================================================
' ContinueSelectFastener - 由 SwitchToPartForm_FA.btnContinue_Click() 调用。
' ============================================================================
Public Sub ContinueSelectFastener()
    If TypeName(CATIA.ActiveDocument) <> "PartDocument" Then
        MsgBox "当前活动文档不是 CATPart。" & Chr(10) & _
               "请先切换到紧固件文档窗口，然后再点击""继续""。", _
               vbExclamation, "快速装配紧固件"
        Exit Sub
    End If

    Unload SwitchToPartForm_FA

    Dim fastenerDoc As Object
    Set fastenerDoc = CATIA.ActiveDocument
    Set g_fastenerDoc = fastenerDoc
    g_fastenerPN = fastenerDoc.Product.PartNumber

    Dim sel As Object
    Set sel = fastenerDoc.Selection
    sel.Clear

    Dim fastEdgeFilter As Variant
    fastEdgeFilter = Array("MonoDim")
    Dim spaFastener As Object
    Set spaFastener = fastenerDoc.GetWorkbench("SPAWorkbench")

    Dim fastEdgeRef As Object
    Dim fastEdgeMeas As Object
    Dim faAxis(2)
    Dim faAnchorPt(2)
    Dim bFaGeomOK As Boolean
    Dim status As String

    Do
        status = sel.SelectElement2(fastEdgeFilter, _
            "请选择紧固件安装面上的圆或圆弧（确定轴向和定位点）[ESC 退出]", False)
        If status <> "Normal" Then Exit Sub

        Set fastEdgeRef = sel.Item(1).Reference
        Set fastEdgeMeas = spaFastener.GetMeasurable(fastEdgeRef)

        bFaGeomOK = TryGetAxis_FA(fastEdgeMeas, faAxis) And TryGetCenter_FA(fastEdgeMeas, faAnchorPt)
        If Not bFaGeomOK Then
            MsgBox "无法从所选元素获取轴向和圆心。" & Chr(10) & _
                   "请选择一个圆或一段圆弧（而非直线或曲线）。", _
                   vbExclamation, "快速装配紧固件"
            sel.Clear
        End If
    Loop While Not bFaGeomOK

    sel.Clear

    Dim faLen As Double
    faLen = Sqr(faAxis(0) * faAxis(0) + faAxis(1) * faAxis(1) + faAxis(2) * faAxis(2))
    If faLen > 0.000000000001 Then
        g_faAxis(0) = faAxis(0) / faLen: g_faAxis(1) = faAxis(1) / faLen: g_faAxis(2) = faAxis(2) / faLen
    Else
        g_faAxis(0) = faAxis(0): g_faAxis(1) = faAxis(1): g_faAxis(2) = faAxis(2)
    End If
    g_faAnchorPt(0) = faAnchorPt(0): g_faAnchorPt(1) = faAnchorPt(1): g_faAnchorPt(2) = faAnchorPt(2)

    If DEBUG_MODE_FA Then
        MsgBox "[DEBUG] 紧固件参考几何" & Chr(10) & _
               "faAxis    = (" & Round(g_faAxis(0), 4) & ", " & Round(g_faAxis(1), 4) & ", " & Round(g_faAxis(2), 4) & ")" & Chr(10) & _
               "faAnchorPt= (" & Round(g_faAnchorPt(0), 4) & ", " & Round(g_faAnchorPt(1), 4) & ", " & Round(g_faAnchorPt(2), 4) & ")", _
               vbInformation, "快速装配紧固件 [DEBUG]"
    End If

    CATIA.StatusBar = "请切换到目标产品（CATProduct）文档窗口，然后点击浮动面板上的""继续""按钮。"
    SwitchDocForm_FA.Show vbModeless
End Sub

' ============================================================================
' ContinueSelectProduct_FA - 由 SwitchDocForm_FA.btnContinue_Click() 调用。
' 只做"选目标产品"这一步，完成后显示 FlipForm_FA 并立即返回。
' 装配循环由用户点击 FlipForm_FA.btnStart 逐孔触发（DoSelectAndPlace_FA）。
' ============================================================================
Public Sub ContinueSelectProduct_FA()
    If TypeName(CATIA.ActiveDocument) <> "ProductDocument" Then
        MsgBox "当前活动文档不是 CATProduct。" & Chr(10) & _
               "请先切换到目标产品文档窗口，然后再点击""继续""。", _
               vbExclamation, "快速装配紧固件"
        Exit Sub
    End If

    Unload SwitchDocForm_FA

    Dim rootDoc As Object
    Set rootDoc = CATIA.ActiveDocument
    Dim sel As Object
    Set sel = rootDoc.Selection
    sel.Clear

    ' 选目标产品/部件
    Dim prodFilter As Variant
    prodFilter = Array("Product")
    Dim status As String
    status = sel.SelectElement2(prodFilter, _
        "在产品结构树中选择紧固件要装入的产品/部件", False)
    If status <> "Normal" Then
        MsgBox "已取消选择。", vbInformation, "快速装配紧固件"
        Exit Sub
    End If

    Set targetProduct_FA = Nothing
    On Error Resume Next
    Set targetProduct_FA = sel.Item(1).Value
    On Error GoTo 0

    If targetProduct_FA Is Nothing Or TypeName(targetProduct_FA) <> "Product" Then
        MsgBox "所选对象不是产品或部件。" & Chr(10) & _
               "请在产品结构树中选择一个产品（Product）或部件。", _
               vbExclamation, "快速装配紧固件"
        sel.Clear
        Exit Sub
    End If

    g_targetPN_FA = targetProduct_FA.PartNumber
    sel.Clear

    ' 初始化装配状态
    g_count_FA = 0
    g_hasLastComp_FA = False
    g_loopActive_FA = True
    g_historyCount_FA = 0
    ReDim g_assemblyHistory_FA(0 To 99, 0 To 7)

    ' 显示装配控制面板；UserForm_Activate 会自动调用 DoSelectAndPlace_FA 开始循环
    FlipForm_FA.Show vbModeless
    FlipForm_FA.btnFlip.Enabled = False
    FlipForm_FA.btnUndo.Enabled = False
    CATIA.StatusBar = "目标产品已选定：" & g_targetPN_FA & "  请选择孔位"
End Sub

' ============================================================================
' DoSelectAndPlace_FA - 由 FlipForm_FA.UserForm_Activate 触发，在 FlipForm_FA 的事件
' 调用栈中执行连续"选孔 → 装配"循环，直到用户按 ESC 或点"退出"为止。
' 因为整个循环在 FlipForm_FA 自身的事件里运行，SelectElement2 等待期间
' CATIA 消息泵正常运转，"翻转"/"撤销"/"退出"全程可响应。
' ============================================================================
Public Sub DoSelectAndPlace_FA()
    If Not g_loopActive_FA Then Exit Sub

    Dim sel As Object
    Dim spaAssembly As Object
    Dim firstFilter As Variant
    Dim holeFilter As Variant
    Dim holeAxis(2)
    Dim holePt(2)
    Dim bHoleGeomOK As Boolean
    Dim status As String
    Dim firstRef As Object
    Dim firstLeafProd As Object
    Dim firstMeas As Object
    Dim holeAxisLen As Double
    Dim ptCoord(2)
    Dim ptAxis(2)
    Dim lineRef As Object
    Dim lineLeafProd As Object
    Dim lineMeas As Object
    Dim lineDir(2)
    Dim lineDirLen As Double
    Dim zeroOff(2)

    firstFilter = Array("MonoDim", "Vertex")
    holeFilter = Array("MonoDim")

    Do While g_loopActive_FA

        Set sel = CATIA.ActiveDocument.Selection
        sel.Clear
        Set spaAssembly = CATIA.ActiveDocument.GetWorkbench("SPAWorkbench")
        bHoleGeomOK = False

        ' ── 选孔位元素（圆形边 或 顶点） ──────────────────────────────────
        status = sel.SelectElement2(firstFilter, _
            "选择孔的圆形边（圆弧模式）或安装锚点顶点（点+线模式） [" & g_fastenerPN & " -> " & g_targetPN_FA & _
            "  已装配:" & g_count_FA & "]  按 ESC 或点""退出""结束", False)

        If status <> "Normal" Or Not g_loopActive_FA Then GoTo ExitLoop

        Set firstRef = sel.Item(1).Reference
        Set firstLeafProd = sel.Item(1).LeafProduct

        If Not TryGetMeasurable_FA(spaAssembly, firstRef, firstMeas) Then
            MsgBox "无法测量所选元素，请重新选择。", vbExclamation, "快速装配紧固件"
            sel.Clear
            GoTo NextRound
        End If

        ' ── 圆弧模式 vs 点+线模式 ───────────────────────────────────────
        If TryGetAxis_FA(firstMeas, holeAxis) And TryGetCenter_FA(firstMeas, holePt) Then
            ' 圆弧模式
            holeAxisLen = Sqr(holeAxis(0) * holeAxis(0) + holeAxis(1) * holeAxis(1) + holeAxis(2) * holeAxis(2))
            If holeAxisLen > 0.000000000001 Then
                holeAxis(0) = holeAxis(0) / holeAxisLen
                holeAxis(1) = holeAxis(1) / holeAxisLen
                holeAxis(2) = holeAxis(2) / holeAxisLen
            End If
            Call TransformToRoot(firstLeafProd, holePt, holeAxis)
            Call TransformToTarget_FA(holePt, holeAxis)
            bHoleGeomOK = True
        ElseIf TryGetPoint_FA(firstMeas, ptCoord) Then
            ' 点+线模式：顶点 + 轴线
            ptAxis(0) = 0: ptAxis(1) = 0: ptAxis(2) = 0
            Call TransformToRoot(firstLeafProd, ptCoord, ptAxis)

            sel.Clear
            status = sel.SelectElement2(holeFilter, _
                "【点+线模式】选择轴线方向（直线或轴线）", False)
            If status <> "Normal" Or Not g_loopActive_FA Then GoTo ExitLoop

            Set lineRef = sel.Item(1).Reference
            Set lineLeafProd = sel.Item(1).LeafProduct

            If TryGetMeasurable_FA(spaAssembly, lineRef, lineMeas) And TryGetDirection_FA(lineMeas, lineDir) Then
                lineDirLen = Sqr(lineDir(0) * lineDir(0) + lineDir(1) * lineDir(1) + lineDir(2) * lineDir(2))
                If lineDirLen > 0.000000000001 Then
                    lineDir(0) = lineDir(0) / lineDirLen
                    lineDir(1) = lineDir(1) / lineDirLen
                    lineDir(2) = lineDir(2) / lineDirLen
                End If
                zeroOff(0) = 0: zeroOff(1) = 0: zeroOff(2) = 0
                Call TransformToRoot(lineLeafProd, zeroOff, lineDir)
                Call TransformToTarget_FA(ptCoord, lineDir)
                holePt(0) = ptCoord(0): holePt(1) = ptCoord(1): holePt(2) = ptCoord(2)
                holeAxis(0) = lineDir(0): holeAxis(1) = lineDir(1): holeAxis(2) = lineDir(2)
                bHoleGeomOK = True
            Else
                MsgBox "无法获取所选直线的方向，请选择一条直线或直线型边。", _
                       vbExclamation, "快速装配紧固件"
            End If
        Else
            MsgBox "无法识别所选元素。" & Chr(10) & _
                   "请选择孔入口处的圆形边，或安装锚点（顶点）。", _
                   vbExclamation, "快速装配紧固件"
        End If

        sel.Clear

        If bHoleGeomOK Then
            g_holeAxisX = holeAxis(0): g_holeAxisY = holeAxis(1): g_holeAxisZ = holeAxis(2)
            g_holePtX_FA = holePt(0):     g_holePtY_FA = holePt(1):     g_holePtZ_FA = holePt(2)

            If DEBUG_MODE_FA Then
                MsgBox "[DEBUG] 孔的几何（targetProduct_FA 局部坐标系）" & Chr(10) & _
                       "holeAxis = (" & Round(holeAxis(0), 4) & ", " & Round(holeAxis(1), 4) & ", " & Round(holeAxis(2), 4) & ")" & Chr(10) & _
                       "holePt   = (" & Round(holePt(0), 4) & ", " & Round(holePt(1), 4) & ", " & Round(holePt(2), 4) & ")", _
                       vbInformation, "快速装配紧固件 [DEBUG]"
            End If

            Call PlaceFastenerAtHole

            CATIA.StatusBar = "已装配 " & g_count_FA & " 个 " & g_fastenerPN & " -> " & g_targetPN_FA & _
                              "  [翻转:" & IIf(g_flipDir_FA, "是", "否") & "]  继续选孔，按 ESC 或点""退出""结束"
        End If

NextRound:
    Loop

ExitLoop:
    g_loopActive_FA = False
    g_hasLastComp_FA = False
    sel.Clear
    ' Unload 和 MsgBox 由 UserForm_Activate 在 DoSelectAndPlace_FA 返回后执行
End Sub

' ============================================================================
' TransformToRoot：将点 pt 和方向向量 dir 从 leafProd 局部坐标系
' 逐层正向变换到根产品坐标系（ProductDocument 层）。
' 方向向量只做旋转，不做平移。
' ============================================================================
Private Sub TransformToRoot(ByVal leafProd As Object, ByRef pt(), ByRef dir())
    Dim curProd As Object
    Set curProd = leafProd
    Dim m(11)
    Dim parentColl As Object
    Dim tx As Double, ty As Double, tz As Double

    Do
        Set parentColl = curProd.Parent
        If TypeName(parentColl) = "ProductDocument" Then Exit Do
        curProd.Position.GetComponents m
        ' 点：旋转 + 平移
        tx = m(0) * pt(0) + m(3) * pt(1) + m(6) * pt(2) + m(9)
        ty = m(1) * pt(0) + m(4) * pt(1) + m(7) * pt(2) + m(10)
        tz = m(2) * pt(0) + m(5) * pt(1) + m(8) * pt(2) + m(11)
        pt(0) = tx: pt(1) = ty: pt(2) = tz
        ' 方向：只旋转
        tx = m(0) * dir(0) + m(3) * dir(1) + m(6) * dir(2)
        ty = m(1) * dir(0) + m(4) * dir(1) + m(7) * dir(2)
        tz = m(2) * dir(0) + m(5) * dir(1) + m(8) * dir(2)
        dir(0) = tx: dir(1) = ty: dir(2) = tz
        Set curProd = parentColl.Parent
    Loop
End Sub

' ============================================================================
' TransformToTarget_FA：将根坐标系中的点 pt 和方向 dir 逆变换到
' targetProduct_FA 局部坐标系。
' ============================================================================
Private Sub TransformToTarget_FA(ByRef pt(), ByRef dir())
    ' 收集 targetProduct_FA → 根 的变换链
    Dim chain(49, 11)
    Dim depth As Integer
    depth = 0
    Dim curProd As Object
    Set curProd = targetProduct_FA
    Dim m(11)
    Dim parentColl As Object
    Dim kk As Integer

    Do
        Set parentColl = curProd.Parent
        If TypeName(parentColl) = "ProductDocument" Then Exit Do
        curProd.Position.GetComponents m
        For kk = 0 To 11: chain(depth, kk) = m(kk): Next kk
        depth = depth + 1
        Set curProd = parentColl.Parent
    Loop

    ' 从根向下（逆序）施加逆变换：local = R^T * (parent - T)
    Dim ii As Integer
    Dim off0 As Double, off1 As Double, off2 As Double
    Dim ax As Double, ay As Double, az As Double

    For ii = depth - 1 To 0 Step -1
        off0 = pt(0) - chain(ii, 9)
        off1 = pt(1) - chain(ii, 10)
        off2 = pt(2) - chain(ii, 11)
        pt(0) = chain(ii, 0) * off0 + chain(ii, 1) * off1 + chain(ii, 2) * off2
        pt(1) = chain(ii, 3) * off0 + chain(ii, 4) * off1 + chain(ii, 5) * off2
        pt(2) = chain(ii, 6) * off0 + chain(ii, 7) * off1 + chain(ii, 8) * off2
        ax = chain(ii, 0) * dir(0) + chain(ii, 1) * dir(1) + chain(ii, 2) * dir(2)
        ay = chain(ii, 3) * dir(0) + chain(ii, 4) * dir(1) + chain(ii, 5) * dir(2)
        az = chain(ii, 6) * dir(0) + chain(ii, 7) * dir(1) + chain(ii, 8) * dir(2)
        dir(0) = ax: dir(1) = ay: dir(2) = az
    Next ii
End Sub

' ============================================================================
' PlaceFastenerAtHole
' ============================================================================
Public Sub PlaceFastenerAtHole()
    Dim insertionDir(2) As Double
    If g_flipDir_FA Then
        insertionDir(0) = -g_holeAxisX: insertionDir(1) = -g_holeAxisY: insertionDir(2) = -g_holeAxisZ
    Else
        insertionDir(0) = g_holeAxisX: insertionDir(1) = g_holeAxisY: insertionDir(2) = g_holeAxisZ
    End If

    Dim holeCenterLocal(2) As Double
    holeCenterLocal(0) = g_holePtX_FA: holeCenterLocal(1) = g_holePtY_FA: holeCenterLocal(2) = g_holePtZ_FA

    Dim f1x(2) As Double, f1y(2) As Double, f1z(2) As Double
    f1z(0) = g_faAxis(0): f1z(1) = g_faAxis(1): f1z(2) = g_faAxis(2)
    Call BuildFrame(f1z, f1x, f1y)

    Dim f2x(2) As Double, f2y(2) As Double, f2z(2) As Double
    f2z(0) = insertionDir(0): f2z(1) = insertionDir(1): f2z(2) = insertionDir(2)
    Call BuildFrame(f2z, f2x, f2y)

    Dim R(2, 2) As Double
    Dim ri As Integer, rj As Integer
    For ri = 0 To 2
        For rj = 0 To 2
            R(ri, rj) = FrameCol_FA(ri, 0, f2x, f2y, f2z) * FrameCol_FA(rj, 0, f1x, f1y, f1z) _
                      + FrameCol_FA(ri, 1, f2x, f2y, f2z) * FrameCol_FA(rj, 1, f1x, f1y, f1z) _
                      + FrameCol_FA(ri, 2, f2x, f2y, f2z) * FrameCol_FA(rj, 2, f1x, f1y, f1z)
        Next rj
    Next ri

    Dim rotatedAnchor(2) As Double
    rotatedAnchor(0) = R(0, 0) * g_faAnchorPt(0) + R(0, 1) * g_faAnchorPt(1) + R(0, 2) * g_faAnchorPt(2)
    rotatedAnchor(1) = R(1, 0) * g_faAnchorPt(0) + R(1, 1) * g_faAnchorPt(1) + R(1, 2) * g_faAnchorPt(2)
    rotatedAnchor(2) = R(2, 0) * g_faAnchorPt(0) + R(2, 1) * g_faAnchorPt(1) + R(2, 2) * g_faAnchorPt(2)

    Dim translation(2) As Double
    translation(0) = holeCenterLocal(0) - rotatedAnchor(0)
    translation(1) = holeCenterLocal(1) - rotatedAnchor(1)
    translation(2) = holeCenterLocal(2) - rotatedAnchor(2)

    Dim products As Object
    Set products = targetProduct_FA.products
    products.AddComponent g_fastenerDoc.Product

    Dim newComp As Object
    Set newComp = products.Item(products.Count)

    Dim moveMatrix(11)
    moveMatrix(0) = R(0, 0): moveMatrix(1) = R(1, 0): moveMatrix(2) = R(2, 0)
    moveMatrix(3) = R(0, 1): moveMatrix(4) = R(1, 1): moveMatrix(5) = R(2, 1)
    moveMatrix(6) = R(0, 2): moveMatrix(7) = R(1, 2): moveMatrix(8) = R(2, 2)
    moveMatrix(9) = translation(0)
    moveMatrix(10) = translation(1)
    moveMatrix(11) = translation(2)

    If DEBUG_MODE_FA Then
        MsgBox "[DEBUG] 最终定位矩阵（targetProduct_FA 坐标系）" & Chr(10) & _
               "R X轴 = (" & Round(R(0, 0), 4) & ", " & Round(R(1, 0), 4) & ", " & Round(R(2, 0), 4) & ")" & Chr(10) & _
               "R Y轴 = (" & Round(R(0, 1), 4) & ", " & Round(R(1, 1), 4) & ", " & Round(R(2, 1), 4) & ")" & Chr(10) & _
               "R Z轴 = (" & Round(R(0, 2), 4) & ", " & Round(R(1, 2), 4) & ", " & Round(R(2, 2), 4) & ")" & Chr(10) & _
               "平移  = (" & Round(translation(0), 4) & ", " & Round(translation(1), 4) & ", " & Round(translation(2), 4) & ")", _
               vbInformation, "快速装配紧固件 [DEBUG]"
    End If

    newComp.Position.SetComponents moveMatrix

    Set g_lastProducts_FA = products
    g_lastCompIdx_FA = products.Count
    g_count_FA = g_count_FA + 1
    g_hasLastComp_FA = True
    FlipForm_FA.btnFlip.Enabled = True

    If g_historyCount_FA < 100 Then
        Set g_assemblyHistory_FA(g_historyCount_FA, 0) = products
        g_assemblyHistory_FA(g_historyCount_FA, 1) = products.Count
        g_assemblyHistory_FA(g_historyCount_FA, 2) = g_holeAxisX
        g_assemblyHistory_FA(g_historyCount_FA, 3) = g_holeAxisY
        g_assemblyHistory_FA(g_historyCount_FA, 4) = g_holeAxisZ
        g_assemblyHistory_FA(g_historyCount_FA, 5) = g_holePtX_FA
        g_assemblyHistory_FA(g_historyCount_FA, 6) = g_holePtY_FA
        g_assemblyHistory_FA(g_historyCount_FA, 7) = g_holePtZ_FA
        g_historyCount_FA = g_historyCount_FA + 1
        FlipForm_FA.btnUndo.Enabled = True
    End If
End Sub

' ============================================================================
' MoveLastFastener
' ============================================================================
Public Sub MoveLastFastener()
    Dim lastComp As Object
    Set lastComp = g_lastProducts_FA.Item(g_lastCompIdx_FA)

    Dim insertionDir(2) As Double
    If g_flipDir_FA Then
        insertionDir(0) = -g_holeAxisX: insertionDir(1) = -g_holeAxisY: insertionDir(2) = -g_holeAxisZ
    Else
        insertionDir(0) = g_holeAxisX: insertionDir(1) = g_holeAxisY: insertionDir(2) = g_holeAxisZ
    End If

    Dim holeCenterLocal(2) As Double
    holeCenterLocal(0) = g_holePtX_FA: holeCenterLocal(1) = g_holePtY_FA: holeCenterLocal(2) = g_holePtZ_FA

    Dim f1x(2) As Double, f1y(2) As Double, f1z(2) As Double
    f1z(0) = g_faAxis(0): f1z(1) = g_faAxis(1): f1z(2) = g_faAxis(2)
    Call BuildFrame(f1z, f1x, f1y)

    Dim f2x(2) As Double, f2y(2) As Double, f2z(2) As Double
    f2z(0) = insertionDir(0): f2z(1) = insertionDir(1): f2z(2) = insertionDir(2)
    Call BuildFrame(f2z, f2x, f2y)

    Dim R(2, 2) As Double
    Dim ri As Integer, rj As Integer
    For ri = 0 To 2
        For rj = 0 To 2
            R(ri, rj) = FrameCol_FA(ri, 0, f2x, f2y, f2z) * FrameCol_FA(rj, 0, f1x, f1y, f1z) _
                      + FrameCol_FA(ri, 1, f2x, f2y, f2z) * FrameCol_FA(rj, 1, f1x, f1y, f1z) _
                      + FrameCol_FA(ri, 2, f2x, f2y, f2z) * FrameCol_FA(rj, 2, f1x, f1y, f1z)
        Next rj
    Next ri

    Dim rotatedAnchor(2) As Double
    rotatedAnchor(0) = R(0, 0) * g_faAnchorPt(0) + R(0, 1) * g_faAnchorPt(1) + R(0, 2) * g_faAnchorPt(2)
    rotatedAnchor(1) = R(1, 0) * g_faAnchorPt(0) + R(1, 1) * g_faAnchorPt(1) + R(1, 2) * g_faAnchorPt(2)
    rotatedAnchor(2) = R(2, 0) * g_faAnchorPt(0) + R(2, 1) * g_faAnchorPt(1) + R(2, 2) * g_faAnchorPt(2)

    Dim translation(2) As Double
    translation(0) = holeCenterLocal(0) - rotatedAnchor(0)
    translation(1) = holeCenterLocal(1) - rotatedAnchor(1)
    translation(2) = holeCenterLocal(2) - rotatedAnchor(2)

    Dim moveMatrix(11)
    moveMatrix(0) = R(0, 0): moveMatrix(1) = R(1, 0): moveMatrix(2) = R(2, 0)
    moveMatrix(3) = R(0, 1): moveMatrix(4) = R(1, 1): moveMatrix(5) = R(2, 1)
    moveMatrix(6) = R(0, 2): moveMatrix(7) = R(1, 2): moveMatrix(8) = R(2, 2)
    moveMatrix(9) = translation(0)
    moveMatrix(10) = translation(1)
    moveMatrix(11) = translation(2)

    lastComp.Position.SetComponents moveMatrix
End Sub

' ============================================================================
' UndoLastFastener
' ============================================================================
Public Sub UndoLastFastener()
    If g_historyCount_FA = 0 Then Exit Sub

    Dim lastIdx As Long
    lastIdx = g_historyCount_FA - 1
    Dim products As Object
    Set products = g_assemblyHistory_FA(lastIdx, 0)
    Dim compIdx As Long
    compIdx = CLng(g_assemblyHistory_FA(lastIdx, 1))

    On Error Resume Next
    products.Remove compIdx
    On Error GoTo 0

    Set g_assemblyHistory_FA(lastIdx, 0) = Nothing
    g_assemblyHistory_FA(lastIdx, 1) = 0
    g_historyCount_FA = g_historyCount_FA - 1
    g_count_FA = g_count_FA - 1

    FlipForm_FA.btnUndo.Enabled = (g_historyCount_FA > 0)
    g_hasLastComp_FA = False
    FlipForm_FA.btnFlip.Enabled = False

    CATIA.StatusBar = "已撤销上一个紧固件。当前已装配: " & g_count_FA & " 个 " & g_fastenerPN
End Sub

' ============================================================================
' BuildFrame
' ============================================================================
Private Sub BuildFrame(ByRef inZ() As Double, ByRef outX() As Double, ByRef outY() As Double)
    Dim zLen As Double
    zLen = Sqr(inZ(0) * inZ(0) + inZ(1) * inZ(1) + inZ(2) * inZ(2))
    If zLen < 0.000000000001 Then
        outX(0) = 1: outX(1) = 0: outX(2) = 0
        outY(0) = 0: outY(1) = 1: outY(2) = 0
        Exit Sub
    End If
    Dim nz(2) As Double
    nz(0) = inZ(0) / zLen: nz(1) = inZ(1) / zLen: nz(2) = inZ(2) / zLen

    Dim refV(2) As Double
    If Abs(nz(0)) < 0.9 Then
        refV(0) = 1: refV(1) = 0: refV(2) = 0
    Else
        refV(0) = 0: refV(1) = 1: refV(2) = 0
    End If

    outX(0) = nz(1) * refV(2) - nz(2) * refV(1)
    outX(1) = nz(2) * refV(0) - nz(0) * refV(2)
    outX(2) = nz(0) * refV(1) - nz(1) * refV(0)
    Dim xLen As Double
    xLen = Sqr(outX(0) * outX(0) + outX(1) * outX(1) + outX(2) * outX(2))
    If xLen < 0.000000000001 Then
        outX(0) = 1: outX(1) = 0: outX(2) = 0
        outY(0) = 0: outY(1) = 1: outY(2) = 0
        Exit Sub
    End If
    outX(0) = outX(0) / xLen: outX(1) = outX(1) / xLen: outX(2) = outX(2) / xLen
    outY(0) = nz(1) * outX(2) - nz(2) * outX(1)
    outY(1) = nz(2) * outX(0) - nz(0) * outX(2)
    outY(2) = nz(0) * outX(1) - nz(1) * outX(0)
End Sub

' ============================================================================
' FrameCol_FA
' ============================================================================
Private Function FrameCol_FA(ByVal row As Integer, ByVal col As Integer, _
                          ByRef vx() As Double, ByRef vy() As Double, _
                          ByRef vz() As Double) As Double
    Select Case col
        Case 0: FrameCol_FA = vx(row)
        Case 1: FrameCol_FA = vy(row)
        Case 2: FrameCol_FA = vz(row)
    End Select
End Function

' ============================================================================
' TryGet* 辅助函数（独立错误域）
' ============================================================================
Private Function TryGetAxis_FA(meas As Object, axArr) As Boolean
    On Error Resume Next: Err.Clear
    meas.GetAxis axArr
    TryGetAxis_FA = (Err.Number = 0)
End Function

Private Function TryGetDirection_FA(meas As Object, dirArr) As Boolean
    On Error Resume Next: Err.Clear
    meas.GetDirection dirArr
    TryGetDirection_FA = (Err.Number = 0)
End Function

Private Function TryGetCenter_FA(meas As Object, ptArr) As Boolean
    On Error Resume Next: Err.Clear
    meas.GetCenter ptArr
    TryGetCenter_FA = (Err.Number = 0)
End Function

Private Function TryGetPoint_FA(meas As Object, ptArr) As Boolean
    On Error Resume Next: Err.Clear
    meas.GetPoint ptArr
    TryGetPoint_FA = (Err.Number = 0)
End Function

Private Function TryGetMeasurable_FA(spa As Object, ref As Object, _
                                  ByRef measOut As Object) As Boolean
    On Error Resume Next: Err.Clear
    Set measOut = spa.GetMeasurable(ref)
    TryGetMeasurable_FA = (Err.Number = 0 And Not measOut Is Nothing)
End Function

Attribute VB_Name = "nut_plate_assembly"
Option Explicit
' nut_plate_assembly - VBA 模块（托板螺母快速装配）
' ── 调试开关：改为 False 关闭所有 [DEBUG] 弹窗（正式使用时设为 False）──────────
Public Const DEBUG_MODE_NP As Boolean = False

' 翻转方向标志；由 FlipForm_NP 按钮切换，跨次运行保持状态：
Public g_flipDir_NP As Boolean

' 对调铆钉孔标志；由 FlipForm_NP 按钮切换，跨次运行保持状态：
' True = 对调，即将第一轴线反向（hole1?hole2 互换），False = 不对调。
Public g_swapHoles_NP As Boolean

'托板螺母参考几何（由 CATMain 读取一次，PlaceNutPlateAtHole 使用）
Public g_bnAxis1(2)         ' 第一轴线（两个铆钉孔圆心连线方向）
Public g_bnAxis2(2)         ' 第二轴线（第一个圆的轴线，已调整为与第一轴线垂直）
Public g_bnAnchorPt(2)      ' 锚点（两个铆钉孔圆心的中点）

' 最近一次孔的几何（选孔后更新，供翻转重装使用）
Public g_holeAxis1X As Double, g_holeAxis1Y As Double, g_holeAxis1Z As Double
Public g_holeAxis2X As Double, g_holeAxis2Y As Double, g_holeAxis2Z As Double
Public g_holePtX_NP    As Double, g_holePtY_NP    As Double, g_holePtZ_NP    As Double

' 最近装配件的删除信息（翻转重装时使用）
Public g_hasLastComp_NP  As Boolean
Public g_lastProducts_NP As Object
Public g_lastCompIdx_NP  As Long

' 装配历史记录（供撤销使用）
Public g_assemblyHistory_NP()         ' 动态数组，存储每个装配件的 Products 集合和索引
Public g_historyCount_NP As Long      ' 历史记录数量

' 装配循环活动标志：ContinueSelectProduct_NP 进入 Do 循环时设为 True，ESC/循环结束时设为 False。
' FlipForm_NP.btnFlip_Click 检查此标志，防止循环结束后残留的 Click 事件切换 g_flipDir_NP。
Public g_loopActive_NP   As Boolean

' 装配循环共享状态
Public targetProduct_NP As Object
Public g_nutPlateDoc As Object
Public g_nutPlatePN  As String
Public g_targetPN_NP      As String
Public g_count_NP         As Long

Public Sub CATMain()
    ' ── 1. 提示用户切换到托板螺母（CATPart）文档（非模态浮动面板）──────────
    CATIA.StatusBar = "请切换到托板螺母（CATPart）文档窗口，然后点击浮动面板上的""继续""按钮。"
    SwitchToPartForm_NP.Show vbModeless
End Sub


' ============================================================================
' ContinueSelectNutPlate - 由 SwitchToPartForm_NP.btnContinue_Click() 调用。
' 在用户切换到托板螺母文档后：选择两个参考圆形边（铆钉孔）+ 读取几何。
' ============================================================================
Public Sub ContinueSelectNutPlate()

    ' 若当前文档不是 CATPart，提示后保持 SwitchToPartForm_NP 打开，不做任何操作
    If TypeName(CATIA.ActiveDocument) <> "PartDocument" Then
        MsgBox "当前活动文档不是 CATPart。" & Chr(10) & _
               "请先切换到托板螺母文档窗口，然后再点击""继续""。", _
               vbExclamation, "快速装配托板螺母"
        Exit Sub
    End If

    Unload SwitchToPartForm_NP

    Dim nutPlateDoc As Object
    Set nutPlateDoc = CATIA.ActiveDocument
    Set g_nutPlateDoc = nutPlateDoc
    g_nutPlatePN = nutPlateDoc.Product.PartNumber

    Dim sel As Object
    Set sel = nutPlateDoc.Selection
    sel.Clear

    ' ── 2. 在托板螺母上选择两个参考圆形边（铆钉孔）──────────────────────
    Dim edgeFilter As Variant
    edgeFilter = Array("MonoDim")
    Dim status As String
    Dim spaNutPlate As Object
    Set spaNutPlate = nutPlateDoc.GetWorkbench("SPAWorkbench")

    Dim edge1Ref As Object, edge2Ref As Object
    Dim edge1Meas As Object, edge2Meas As Object
    Dim center1(2), center2(2)
    Dim axis1(2), axis2(2)
    Dim bGeomOK As Boolean

    ' ── 选择第一个圆（铆钉孔1）──────────────────────────────────────────
    Do
        status = sel.SelectElement2(edgeFilter, _
            "请选择托板螺母安装面的第一个铆钉孔（圆或圆弧）[ESC 退出]", False)
        If status <> "Normal" Then Exit Sub

        Set edge1Ref = sel.Item(1).Reference
        Set edge1Meas = spaNutPlate.GetMeasurable(edge1Ref)

        bGeomOK = TryGetAxis_NP(edge1Meas, axis1) And TryGetCenter_NP(edge1Meas, center1)
        If Not bGeomOK Then
            MsgBox "无法从所选元素获取轴向和圆心。" & Chr(10) & _
                   "请选择一个圆或一段圆弧（而非直线或曲线）。", _
                   vbExclamation, "快速装配托板螺母"
            sel.Clear
        End If
    Loop While Not bGeomOK

    ' ── 选择第二个圆（铆钉孔2）──────────────────────────────────────────
    Do
        status = sel.SelectElement2(edgeFilter, _
            "请选择托板螺母安装面的第二个铆钉孔（圆或圆弧）[ESC 退出]", False)
        If status <> "Normal" Then Exit Sub

        Set edge2Ref = sel.Item(1).Reference
        Set edge2Meas = spaNutPlate.GetMeasurable(edge2Ref)

        bGeomOK = TryGetCenter_NP(edge2Meas, center2)
        If Not bGeomOK Then
            MsgBox "无法从所选元素获取圆心。" & Chr(10) & _
                   "请选择一个圆或一段圆弧（而非直线或曲线）。", _
                   vbExclamation, "快速装配托板螺母"
            sel.Clear
        End If
    Loop While Not bGeomOK

    sel.Clear

    ' ── 3. 计算托板螺母的参考几何 ────────────────────────────────────────
    ' 锚点 = 两个圆心的中点
    Dim anchorPt(2) As Double
    anchorPt(0) = (center1(0) + center2(0)) / 2
    anchorPt(1) = (center1(1) + center2(1)) / 2
    anchorPt(2) = (center1(2) + center2(2)) / 2

    ' 第一轴线 = 两个圆心连线的方向（从 center1 指向 center2）
    Dim bnAxis1(2) As Double
    bnAxis1(0) = center2(0) - center1(0)
    bnAxis1(1) = center2(1) - center1(1)
    bnAxis1(2) = center2(2) - center1(2)
    ' 归一化第一轴线
    Dim axis1Len As Double
    axis1Len = Sqr(bnAxis1(0) * bnAxis1(0) + bnAxis1(1) * bnAxis1(1) + bnAxis1(2) * bnAxis1(2))
    If axis1Len < 0.000000000001 Then
        MsgBox "两个铆钉孔的圆心重合，无法确定第一轴线。", vbExclamation, "快速装配托板螺母"
        Exit Sub
    End If
    bnAxis1(0) = bnAxis1(0) / axis1Len
    bnAxis1(1) = bnAxis1(1) / axis1Len
    bnAxis1(2) = bnAxis1(2) / axis1Len

    ' 第二轴线 = 第一个圆的轴线方向（axis1），需调整为与第一轴线垂直
    ' 归一化第一个圆的轴线
    Dim circleAxisLen As Double
    circleAxisLen = Sqr(axis1(0) * axis1(0) + axis1(1) * axis1(1) + axis1(2) * axis1(2))
    If circleAxisLen > 0.000000000001 Then
        axis1(0) = axis1(0) / circleAxisLen
        axis1(1) = axis1(1) / circleAxisLen
        axis1(2) = axis1(2) / circleAxisLen
    End If

    ' 在第一轴线和第一个圆轴线决定的平面内，调整第二轴线使其与第一轴线垂直
    ' 方法：第二轴线 = axis1 - (axis1·bnAxis1) * bnAxis1（投影到垂直于 bnAxis1 的分量）
    Dim dotProduct As Double
    dotProduct = axis1(0) * bnAxis1(0) + axis1(1) * bnAxis1(1) + axis1(2) * bnAxis1(2)
    Dim bnAxis2(2) As Double
    bnAxis2(0) = axis1(0) - dotProduct * bnAxis1(0)
    bnAxis2(1) = axis1(1) - dotProduct * bnAxis1(1)
    bnAxis2(2) = axis1(2) - dotProduct * bnAxis1(2)
    ' 归一化第二轴线
    Dim axis2Len As Double
    axis2Len = Sqr(bnAxis2(0) * bnAxis2(0) + bnAxis2(1) * bnAxis2(1) + bnAxis2(2) * bnAxis2(2))
    If axis2Len < 0.000000000001 Then
        ' 如果第一个圆的轴线与第一轴线平行，则第二轴线无法确定，选择一个垂直方向
        MsgBox "第一个铆钉孔的轴线与两圆心连线平行，无法确定第二轴线。", vbExclamation, "快速装配托板螺母"
        Exit Sub
    End If
    bnAxis2(0) = bnAxis2(0) / axis2Len
    bnAxis2(1) = bnAxis2(1) / axis2Len
    bnAxis2(2) = bnAxis2(2) / axis2Len

    ' 写入模块级变量
    g_bnAnchorPt(0) = anchorPt(0): g_bnAnchorPt(1) = anchorPt(1): g_bnAnchorPt(2) = anchorPt(2)
    g_bnAxis1(0) = bnAxis1(0): g_bnAxis1(1) = bnAxis1(1): g_bnAxis1(2) = bnAxis1(2)
    g_bnAxis2(0) = bnAxis2(0): g_bnAxis2(1) = bnAxis2(1): g_bnAxis2(2) = bnAxis2(2)

    ' ── 调试：托板螺母参考几何 ────────────────────────────────────────────
    If DEBUG_MODE_NP Then
        MsgBox "[DEBUG]托板螺母参考几何" & Chr(10) & _
               "锚点     = (" & Round(g_bnAnchorPt(0), 4) & ", " & Round(g_bnAnchorPt(1), 4) & ", " & Round(g_bnAnchorPt(2), 4) & ")" & Chr(10) & _
               "第一轴线 = (" & Round(g_bnAxis1(0), 4) & ", " & Round(g_bnAxis1(1), 4) & ", " & Round(g_bnAxis1(2), 4) & ")" & Chr(10) & _
               "第二轴线 = (" & Round(g_bnAxis2(0), 4) & ", " & Round(g_bnAxis2(1), 4) & ", " & Round(g_bnAxis2(2), 4) & ")", _
               vbInformation, "快速装配托板螺母[DEBUG]"
    End If

    ' ── 4. 等待用户切换到产品文档（非模态浮动面板）────────────────────
    CATIA.StatusBar = "请切换到目标产品（CATProduct）文档窗口，然后点击浮动面板上的""继续""按钮。"
    SwitchDocForm_NP.Show vbModeless

End Sub

' ============================================================================
' ContinueSelectProduct_NP - 由 SwitchDocForm_NP.btnContinue_Click() 调用。
' 只做"选目标产品"这一步，完成后显示 FlipForm_NP 并立即返回。
' 装配循环由 FlipForm_NP.UserForm_Activate 触发的 DoSelectAndPlace_NP 执行。
' ============================================================================
Public Sub ContinueSelectProduct_NP()

    If TypeName(CATIA.ActiveDocument) <> "ProductDocument" Then
        MsgBox "当前活动文档不是 CATProduct。" & Chr(10) & _
               "请先切换到目标产品文档窗口，然后再点击""继续""。", _
               vbExclamation, "快速装配托板螺母"
        Exit Sub
    End If

    Unload SwitchDocForm_NP

    Dim rootDoc As Object
    Set rootDoc = CATIA.ActiveDocument
    Dim sel As Object
    Set sel = rootDoc.Selection
    sel.Clear

    Dim prodFilter As Variant
    prodFilter = Array("Product")
    Dim status As String
    status = sel.SelectElement2(prodFilter, _
        "在产品结构树中选择托板螺母要装入的产品/部件", False)
    If status <> "Normal" Then
        MsgBox "已取消选择。", vbInformation, "快速装配托板螺母"
        Exit Sub
    End If

    Set targetProduct_NP = Nothing
    On Error Resume Next
    Set targetProduct_NP = sel.Item(1).Value
    On Error GoTo 0

    If targetProduct_NP Is Nothing Or TypeName(targetProduct_NP) <> "Product" Then
        MsgBox "所选对象不是产品或部件。" & Chr(10) & _
               "请在产品结构树中选择一个产品（Product）或部件。", _
               vbExclamation, "快速装配托板螺母"
        sel.Clear
        Exit Sub
    End If

    g_targetPN_NP = targetProduct_NP.PartNumber
    sel.Clear

    ' 初始化装配状态
    g_count_NP = 0
    g_hasLastComp_NP = False
    g_loopActive_NP = True
    g_historyCount_NP = 0
    ReDim g_assemblyHistory_NP(0 To 99, 0 To 10)

    ' 显示装配控制面板；UserForm_Activate 会自动调用 DoSelectAndPlace_NP 开始循环
    FlipForm_NP.Show vbModeless
    FlipForm_NP.btnFlip.Enabled = False
    FlipForm_NP.btnSwap.Enabled = False
    FlipForm_NP.btnUndo.Enabled = False
    CATIA.StatusBar = "目标产品已选定：" & g_targetPN_NP & "  请选择安装孔"

End Sub

' ============================================================================
' DoSelectAndPlace_NP - 由 FlipForm_NP.UserForm_Activate 触发，在 FlipForm_NP 的事件
' 调用栈中执行连续"选孔 → 装配"循环，直到用户按 ESC 或点"退出"为止。
' 因为整个循环在 FlipForm_NP 自身的事件里运行，SelectElement2 等待期间
' CATIA 消息泵正常运转，"翻转"/"对调"/"撤销"/"退出"全程可响应。
' ============================================================================
Public Sub DoSelectAndPlace_NP()
    If Not g_loopActive_NP Then Exit Sub

    Dim sel As Object
    Dim spaAssembly As Object
    Dim firstFilter As Variant
    Dim holeFilter As Variant
    Dim ptFilter As Variant
    Dim holePt(2) As Double
    Dim holeAxis1(2) As Double
    Dim holeAxis2(2) As Double
    Dim bHoleGeomOK As Boolean
    Dim status As String

    firstFilter = Array("MonoDim", "Vertex")
    holeFilter = Array("MonoDim")
    ptFilter = Array("Vertex")

    Do While g_loopActive_NP

        Set sel = CATIA.ActiveDocument.Selection
        sel.Clear
        Set spaAssembly = CATIA.ActiveDocument.GetWorkbench("SPAWorkbench")
        bHoleGeomOK = False

        ' ── 第一步：选择第一个元素（圆形边 或 锚点顶点）────────────────────────
        status = sel.SelectElement2(firstFilter, _
            "选择安装孔的第一个圆（圆弧模式）或第一个锚点顶点（点+线模式） [" & g_nutPlatePN & " -> " & g_targetPN_NP & _
            "  已装配:" & g_count_NP & "]  按 ESC 或点""退出""结束", False)
        If status <> "Normal" Or Not g_loopActive_NP Then GoTo ExitLoop

        Dim firstRef As Object: Set firstRef = sel.Item(1).Reference
        Dim firstLeafProd As Object: Set firstLeafProd = sel.Item(1).LeafProduct
        Dim firstMeas As Object

        If Not TryGetMeasurable_NP(spaAssembly, firstRef, firstMeas) Then
            MsgBox "无法测量所选元素，请重新选择。", vbExclamation, "快速装配托板螺母"
            sel.Clear
            GoTo NextRound
        End If

        Dim hole1Meas As Object, hole2Ref As Object, hole2Meas As Object
        Dim holeCenter1(2), holeCenter2(2)
        Dim axis1Raw(2)
        Set hole1Meas = firstMeas

        If TryGetCenter_NP(hole1Meas, holeCenter1) And TryGetAxis_NP(hole1Meas, axis1Raw) Then
            ' ── 圆弧模式 ──────────────────────────────────────────────────────
            Dim h1M(11), h1Tx As Double, h1Ty As Double, h1Tz As Double
            Dim h1Cur As Object: Set h1Cur = firstLeafProd
            Dim h1Par As Object
            Do
                Set h1Par = h1Cur.Parent
                If TypeName(h1Par) = "ProductDocument" Then Exit Do
                h1Cur.Position.GetComponents h1M
                h1Tx = h1M(0) * holeCenter1(0) + h1M(3) * holeCenter1(1) + h1M(6) * holeCenter1(2) + h1M(9)
                h1Ty = h1M(1) * holeCenter1(0) + h1M(4) * holeCenter1(1) + h1M(7) * holeCenter1(2) + h1M(10)
                h1Tz = h1M(2) * holeCenter1(0) + h1M(5) * holeCenter1(1) + h1M(8) * holeCenter1(2) + h1M(11)
                holeCenter1(0) = h1Tx: holeCenter1(1) = h1Ty: holeCenter1(2) = h1Tz
                h1Tx = h1M(0) * axis1Raw(0) + h1M(3) * axis1Raw(1) + h1M(6) * axis1Raw(2)
                h1Ty = h1M(1) * axis1Raw(0) + h1M(4) * axis1Raw(1) + h1M(7) * axis1Raw(2)
                h1Tz = h1M(2) * axis1Raw(0) + h1M(5) * axis1Raw(1) + h1M(8) * axis1Raw(2)
                axis1Raw(0) = h1Tx: axis1Raw(1) = h1Ty: axis1Raw(2) = h1Tz
                Set h1Cur = h1Par.Parent
            Loop

            ' 选择第二个圆
            status = sel.SelectElement2(holeFilter, _
                "选择安装孔的第二个圆 [" & g_nutPlatePN & " -> " & g_targetPN_NP & _
                "  已装配:" & g_count_NP & "]  按 ESC 或点""退出""结束", False)
            If status <> "Normal" Or Not g_loopActive_NP Then GoTo ExitLoop

            Set hole2Ref = sel.Item(1).Reference
            Dim hole2LeafProd As Object: Set hole2LeafProd = sel.Item(1).LeafProduct
            bHoleGeomOK = False
            If TryGetMeasurable_NP(spaAssembly, hole2Ref, hole2Meas) Then
                bHoleGeomOK = TryGetCenter_NP(hole2Meas, holeCenter2)
            End If

            If Not bHoleGeomOK Then
                MsgBox "无法获取第二个安装孔的圆心，请重新选择。", vbExclamation, "快速装配托板螺母"
                sel.Clear
            Else
                ' 将 center2 推导到根坐标系
                Dim h2M(11), h2Tx As Double, h2Ty As Double, h2Tz As Double
                Dim h2Cur As Object: Set h2Cur = hole2LeafProd
                Dim h2Par As Object
                Do
                    Set h2Par = h2Cur.Parent
                    If TypeName(h2Par) = "ProductDocument" Then Exit Do
                    h2Cur.Position.GetComponents h2M
                    h2Tx = h2M(0) * holeCenter2(0) + h2M(3) * holeCenter2(1) + h2M(6) * holeCenter2(2) + h2M(9)
                    h2Ty = h2M(1) * holeCenter2(0) + h2M(4) * holeCenter2(1) + h2M(7) * holeCenter2(2) + h2M(10)
                    h2Tz = h2M(2) * holeCenter2(0) + h2M(5) * holeCenter2(1) + h2M(8) * holeCenter2(2) + h2M(11)
                    holeCenter2(0) = h2Tx: holeCenter2(1) = h2Ty: holeCenter2(2) = h2Tz
                    Set h2Cur = h2Par.Parent
                Loop

                ' 计算中点、第一轴线、第二轴线（根坐标系）
                Dim circleMidPt(2)
                circleMidPt(0) = (holeCenter1(0) + holeCenter2(0)) / 2
                circleMidPt(1) = (holeCenter1(1) + holeCenter2(1)) / 2
                circleMidPt(2) = (holeCenter1(2) + holeCenter2(2)) / 2
                Dim circleAxis1(2)
                circleAxis1(0) = holeCenter2(0) - holeCenter1(0)
                circleAxis1(1) = holeCenter2(1) - holeCenter1(1)
                circleAxis1(2) = holeCenter2(2) - holeCenter1(2)
                Dim circleAxis1Len As Double
                circleAxis1Len = Sqr(circleAxis1(0) * circleAxis1(0) + circleAxis1(1) * circleAxis1(1) + circleAxis1(2) * circleAxis1(2))
                If circleAxis1Len < 0.000000000001 Then
                    MsgBox "两个安装孔的圆心重合，无法确定第一轴线。", vbExclamation, "快速装配托板螺母"
                    sel.Clear
                    bHoleGeomOK = False
                Else
                    circleAxis1(0) = circleAxis1(0) / circleAxis1Len
                    circleAxis1(1) = circleAxis1(1) / circleAxis1Len
                    circleAxis1(2) = circleAxis1(2) / circleAxis1Len
                    Dim ax1RLen As Double
                    ax1RLen = Sqr(axis1Raw(0) * axis1Raw(0) + axis1Raw(1) * axis1Raw(1) + axis1Raw(2) * axis1Raw(2))
                    If ax1RLen > 0.000000000001 Then
                        axis1Raw(0) = axis1Raw(0) / ax1RLen
                        axis1Raw(1) = axis1Raw(1) / ax1RLen
                        axis1Raw(2) = axis1Raw(2) / ax1RLen
                    End If
                    Dim hDP As Double
                    hDP = axis1Raw(0) * circleAxis1(0) + axis1Raw(1) * circleAxis1(1) + axis1Raw(2) * circleAxis1(2)
                    Dim circleAxis2(2)
                    circleAxis2(0) = axis1Raw(0) - hDP * circleAxis1(0)
                    circleAxis2(1) = axis1Raw(1) - hDP * circleAxis1(1)
                    circleAxis2(2) = axis1Raw(2) - hDP * circleAxis1(2)
                    Dim circleAxis2Len As Double
                    circleAxis2Len = Sqr(circleAxis2(0) * circleAxis2(0) + circleAxis2(1) * circleAxis2(1) + circleAxis2(2) * circleAxis2(2))
                    If circleAxis2Len < 0.000000000001 Then
                        MsgBox "第一个安装孔的轴线与两圆心连线平行，无法确定第二轴线。", vbExclamation, "快速装配托板螺母"
                        sel.Clear
                        bHoleGeomOK = False
                    Else
                        circleAxis2(0) = circleAxis2(0) / circleAxis2Len
                        circleAxis2(1) = circleAxis2(1) / circleAxis2Len
                        circleAxis2(2) = circleAxis2(2) / circleAxis2Len
                        ' 逆变换到 targetProduct_NP 坐标系
                        Call TransformToTarget_NP(circleMidPt, circleAxis1, circleAxis2)
                        holePt(0) = circleMidPt(0):     holePt(1) = circleMidPt(1):     holePt(2) = circleMidPt(2)
                        holeAxis1(0) = circleAxis1(0):  holeAxis1(1) = circleAxis1(1):  holeAxis1(2) = circleAxis1(2)
                        holeAxis2(0) = circleAxis2(0):  holeAxis2(1) = circleAxis2(1):  holeAxis2(2) = circleAxis2(2)
                        bHoleGeomOK = True
                    End If
                End If
            End If  ' bHoleGeomOK (second circle)

        ElseIf TryGetPoint_NP(firstMeas, holeCenter1) Then
            ' ── 点+线模式 ──────────────────────────────────────────────────────
            ' 将第一个点推导到根坐标系
            Dim np1Cur As Object: Set np1Cur = firstLeafProd
            Dim np1M(11): Dim np1Par As Object
            Dim np1Tx As Double, np1Ty As Double, np1Tz As Double
            Do
                Set np1Par = np1Cur.Parent
                If TypeName(np1Par) = "ProductDocument" Then Exit Do
                np1Cur.Position.GetComponents np1M
                np1Tx = np1M(0) * holeCenter1(0) + np1M(3) * holeCenter1(1) + np1M(6) * holeCenter1(2) + np1M(9)
                np1Ty = np1M(1) * holeCenter1(0) + np1M(4) * holeCenter1(1) + np1M(7) * holeCenter1(2) + np1M(10)
                np1Tz = np1M(2) * holeCenter1(0) + np1M(5) * holeCenter1(1) + np1M(8) * holeCenter1(2) + np1M(11)
                holeCenter1(0) = np1Tx: holeCenter1(1) = np1Ty: holeCenter1(2) = np1Tz
                Set np1Cur = np1Par.Parent
            Loop

            ' 选择第二个点
            sel.Clear
            status = sel.SelectElement2(ptFilter, "【点+线模式】第2步：选择第二个点", False)
            If status <> "Normal" Or Not g_loopActive_NP Then GoTo ExitLoop

            Dim np2Ref As Object: Set np2Ref = sel.Item(1).Reference
            Dim np2LeafProd As Object: Set np2LeafProd = sel.Item(1).LeafProduct
            Dim np2Meas As Object
            If Not (TryGetMeasurable_NP(spaAssembly, np2Ref, np2Meas) And TryGetPoint_NP(np2Meas, holeCenter2)) Then
                MsgBox "无法获取第二个点的坐标，请选择顶点或点要素。", vbExclamation, "快速装配托板螺母"
                sel.Clear
                GoTo NextRound
            End If
            ' 将第二个点推导到根坐标系
            Dim np2Cur As Object: Set np2Cur = np2LeafProd
            Dim np2M(11): Dim np2Par As Object
            Dim np2Tx As Double, np2Ty As Double, np2Tz As Double
            Do
                Set np2Par = np2Cur.Parent
                If TypeName(np2Par) = "ProductDocument" Then Exit Do
                np2Cur.Position.GetComponents np2M
                np2Tx = np2M(0) * holeCenter2(0) + np2M(3) * holeCenter2(1) + np2M(6) * holeCenter2(2) + np2M(9)
                np2Ty = np2M(1) * holeCenter2(0) + np2M(4) * holeCenter2(1) + np2M(7) * holeCenter2(2) + np2M(10)
                np2Tz = np2M(2) * holeCenter2(0) + np2M(5) * holeCenter2(1) + np2M(8) * holeCenter2(2) + np2M(11)
                holeCenter2(0) = np2Tx: holeCenter2(1) = np2Ty: holeCenter2(2) = np2Tz
                Set np2Cur = np2Par.Parent
            Loop

            ' 选择轴线方向
            sel.Clear
            status = sel.SelectElement2(holeFilter, "【点+线模式】第3步：选择轴线方向（直线或轴线）", False)
            If status <> "Normal" Or Not g_loopActive_NP Then GoTo ExitLoop

            Dim npLnRef As Object: Set npLnRef = sel.Item(1).Reference
            Dim npLnLeafProd As Object: Set npLnLeafProd = sel.Item(1).LeafProduct
            Dim npLnMeas As Object
            Dim npLnDir(2)
            If Not (TryGetMeasurable_NP(spaAssembly, npLnRef, npLnMeas) And TryGetDirection_NP(npLnMeas, npLnDir)) Then
                MsgBox "无法获取所选直线的方向，请选择直线或直线型边。", vbExclamation, "快速装配托板螺母"
                sel.Clear
                GoTo NextRound
            End If
            Dim npLnDirLen As Double
            npLnDirLen = Sqr(npLnDir(0) * npLnDir(0) + npLnDir(1) * npLnDir(1) + npLnDir(2) * npLnDir(2))
            If npLnDirLen > 0.000000000001 Then
                npLnDir(0) = npLnDir(0) / npLnDirLen: npLnDir(1) = npLnDir(1) / npLnDirLen: npLnDir(2) = npLnDir(2) / npLnDirLen
            End If
            ' 将轴线方向推导到根坐标系（只旋转）
            Dim npLnCur As Object: Set npLnCur = npLnLeafProd
            Dim npLnM(11): Dim npLnPar As Object
            Dim npLnTx As Double, npLnTy As Double, npLnTz As Double
            Do
                Set npLnPar = npLnCur.Parent
                If TypeName(npLnPar) = "ProductDocument" Then Exit Do
                npLnCur.Position.GetComponents npLnM
                npLnTx = npLnM(0) * npLnDir(0) + npLnM(3) * npLnDir(1) + npLnM(6) * npLnDir(2)
                npLnTy = npLnM(1) * npLnDir(0) + npLnM(4) * npLnDir(1) + npLnM(7) * npLnDir(2)
                npLnTz = npLnM(2) * npLnDir(0) + npLnM(5) * npLnDir(1) + npLnM(8) * npLnDir(2)
                npLnDir(0) = npLnTx: npLnDir(1) = npLnTy: npLnDir(2) = npLnTz
                Set npLnCur = npLnPar.Parent
            Loop

            ' 计算中点、第一轴线、第二轴线（根坐标系）
            Dim pointModeMidPt(2)
            pointModeMidPt(0) = (holeCenter1(0) + holeCenter2(0)) / 2
            pointModeMidPt(1) = (holeCenter1(1) + holeCenter2(1)) / 2
            pointModeMidPt(2) = (holeCenter1(2) + holeCenter2(2)) / 2
            Dim pointModeAxis1(2)
            pointModeAxis1(0) = holeCenter2(0) - holeCenter1(0)
            pointModeAxis1(1) = holeCenter2(1) - holeCenter1(1)
            pointModeAxis1(2) = holeCenter2(2) - holeCenter1(2)
            Dim pointModeAxis1Len As Double
            pointModeAxis1Len = Sqr(pointModeAxis1(0) * pointModeAxis1(0) + pointModeAxis1(1) * pointModeAxis1(1) + pointModeAxis1(2) * pointModeAxis1(2))
            If pointModeAxis1Len < 0.000000000001 Then
                MsgBox "两个点重合，无法确定第一轴线。", vbExclamation, "快速装配托板螺母"
                sel.Clear
                GoTo NextRound
            End If
            pointModeAxis1(0) = pointModeAxis1(0) / pointModeAxis1Len
            pointModeAxis1(1) = pointModeAxis1(1) / pointModeAxis1Len
            pointModeAxis1(2) = pointModeAxis1(2) / pointModeAxis1Len
            Dim np2DP As Double
            np2DP = npLnDir(0) * pointModeAxis1(0) + npLnDir(1) * pointModeAxis1(1) + npLnDir(2) * pointModeAxis1(2)
            Dim pointModeAxis2(2)
            pointModeAxis2(0) = npLnDir(0) - np2DP * pointModeAxis1(0)
            pointModeAxis2(1) = npLnDir(1) - np2DP * pointModeAxis1(1)
            pointModeAxis2(2) = npLnDir(2) - np2DP * pointModeAxis1(2)
            Dim pointModeAxis2Len As Double
            pointModeAxis2Len = Sqr(pointModeAxis2(0) * pointModeAxis2(0) + pointModeAxis2(1) * pointModeAxis2(1) + pointModeAxis2(2) * pointModeAxis2(2))
            If pointModeAxis2Len < 0.000000000001 Then
                MsgBox "所选轴线方向与两点连线平行，无法确定第二轴线。", vbExclamation, "快速装配托板螺母"
                sel.Clear
                GoTo NextRound
            End If
            pointModeAxis2(0) = pointModeAxis2(0) / pointModeAxis2Len
            pointModeAxis2(1) = pointModeAxis2(1) / pointModeAxis2Len
            pointModeAxis2(2) = pointModeAxis2(2) / pointModeAxis2Len
            ' 逆变换到 targetProduct_NP 坐标系
            Call TransformToTarget_NP(pointModeMidPt, pointModeAxis1, pointModeAxis2)
            holePt(0) = pointModeMidPt(0):      holePt(1) = pointModeMidPt(1):      holePt(2) = pointModeMidPt(2)
            holeAxis1(0) = pointModeAxis1(0):   holeAxis1(1) = pointModeAxis1(1):   holeAxis1(2) = pointModeAxis1(2)
            holeAxis2(0) = pointModeAxis2(0):   holeAxis2(1) = pointModeAxis2(1):   holeAxis2(2) = pointModeAxis2(2)
            bHoleGeomOK = True

        Else
            MsgBox "无法识别所选元素。" & Chr(10) & _
                   "请选择安装孔的圆形边（圆弧/圆），或选择安装锚点（顶点/点）。", _
                   vbExclamation, "快速装配托板螺母"
            sel.Clear
        End If

        sel.Clear

        If bHoleGeomOK Then
            g_holeAxis1X = holeAxis1(0): g_holeAxis1Y = holeAxis1(1): g_holeAxis1Z = holeAxis1(2)
            g_holeAxis2X = holeAxis2(0): g_holeAxis2Y = holeAxis2(1): g_holeAxis2Z = holeAxis2(2)
            g_holePtX_NP = holePt(0):       g_holePtY_NP = holePt(1):       g_holePtZ_NP = holePt(2)

            If DEBUG_MODE_NP Then
                MsgBox "[DEBUG] 安装孔几何（targetProduct_NP 局部坐标系）" & Chr(10) & _
                       "锚点     = (" & Round(holePt(0), 4) & ", " & Round(holePt(1), 4) & ", " & Round(holePt(2), 4) & ")" & Chr(10) & _
                       "第一轴线 = (" & Round(holeAxis1(0), 4) & ", " & Round(holeAxis1(1), 4) & ", " & Round(holeAxis1(2), 4) & ")" & Chr(10) & _
                       "第二轴线 = (" & Round(holeAxis2(0), 4) & ", " & Round(holeAxis2(1), 4) & ", " & Round(holeAxis2(2), 4) & ")", _
                       vbInformation, "快速装配托板螺母[DEBUG]"
            End If

            Call PlaceNutPlateAtHole

            CATIA.StatusBar = "已装配 " & g_count_NP & " 个 " & g_nutPlatePN & " -> " & g_targetPN_NP & _
                              "  [翻转:" & IIf(g_flipDir_NP, "是", "否") & _
                              "  对调:" & IIf(g_swapHoles_NP, "是", "否") & "]" & _
                              "  继续选孔，按 ESC 或点""退出""结束"
        End If

NextRound:
    Loop

ExitLoop:
    g_loopActive_NP = False
    g_hasLastComp_NP = False
    sel.Clear
    ' Unload 和 MsgBox 由 UserForm_Activate 在 DoSelectAndPlace_NP 返回后执行
End Sub

' ============================================================================
' TransformToTarget_NP：将根坐标系中的点 pt 和两个方向向量 dir1/dir2
' 逆变换到 targetProduct_NP 局部坐标系。
' ============================================================================
Private Sub TransformToTarget_NP(ByRef pt(), ByRef dir1(), ByRef dir2())
    Dim chain(49, 11)
    Dim depth As Integer: depth = 0
    Dim curProd As Object: Set curProd = targetProduct_NP
    Dim m(11): Dim parentColl As Object: Dim kk As Integer
    Do
        Set parentColl = curProd.Parent
        If TypeName(parentColl) = "ProductDocument" Then Exit Do
        curProd.Position.GetComponents m
        For kk = 0 To 11: chain(depth, kk) = m(kk): Next kk
        depth = depth + 1
        Set curProd = parentColl.Parent
    Loop
    Dim ii As Integer
    Dim off0 As Double, off1 As Double, off2 As Double
    Dim ax As Double, ay As Double, az As Double
    For ii = depth - 1 To 0 Step -1
        off0 = pt(0) - chain(ii, 9): off1 = pt(1) - chain(ii, 10): off2 = pt(2) - chain(ii, 11)
        pt(0) = chain(ii, 0) * off0 + chain(ii, 1) * off1 + chain(ii, 2) * off2
        pt(1) = chain(ii, 3) * off0 + chain(ii, 4) * off1 + chain(ii, 5) * off2
        pt(2) = chain(ii, 6) * off0 + chain(ii, 7) * off1 + chain(ii, 8) * off2
        ax = chain(ii, 0) * dir1(0) + chain(ii, 1) * dir1(1) + chain(ii, 2) * dir1(2)
        ay = chain(ii, 3) * dir1(0) + chain(ii, 4) * dir1(1) + chain(ii, 5) * dir1(2)
        az = chain(ii, 6) * dir1(0) + chain(ii, 7) * dir1(1) + chain(ii, 8) * dir1(2)
        dir1(0) = ax: dir1(1) = ay: dir1(2) = az
        ax = chain(ii, 0) * dir2(0) + chain(ii, 1) * dir2(1) + chain(ii, 2) * dir2(2)
        ay = chain(ii, 3) * dir2(0) + chain(ii, 4) * dir2(1) + chain(ii, 5) * dir2(2)
        az = chain(ii, 6) * dir2(0) + chain(ii, 7) * dir2(1) + chain(ii, 8) * dir2(2)
        dir2(0) = ax: dir2(1) = ay: dir2(2) = az
    Next ii
End Sub


' ============================================================================
' PlaceNutPlateAtHole：根据模块级变量中存储的孔几何和托板螺母参数，
' 计算变换矩阵并添加一个托板螺母实例。
'
' 读取：g_flipDir_NP, g_bnAxis1, g_bnAxis2, g_bnAnchorPt（托板螺母局部坐标系），
'        g_holeAxis1X/Y/Z, g_holeAxis2X/Y/Z, g_holePtX_NP/Y/Z（均为 targetProduct_NP 坐标系），
'        targetProduct_NP
' 写入：g_count_NP（+1），g_lastProducts_NP，g_lastCompIdx_NP
' ============================================================================
Public Sub PlaceNutPlateAtHole()

    ' 根据 g_flipDir_NP 决定第二轴线的方向（翻转意味着第二轴线反向）
    Dim holeAxis2Dir(2) As Double
    If g_flipDir_NP Then
        holeAxis2Dir(0) = -g_holeAxis2X
        holeAxis2Dir(1) = -g_holeAxis2Y
        holeAxis2Dir(2) = -g_holeAxis2Z
    Else
        holeAxis2Dir(0) = g_holeAxis2X
        holeAxis2Dir(1) = g_holeAxis2Y
        holeAxis2Dir(2) = g_holeAxis2Z
    End If

    Dim holeCenterLocal(2) As Double
    holeCenterLocal(0) = g_holePtX_NP: holeCenterLocal(1) = g_holePtY_NP: holeCenterLocal(2) = g_holePtZ_NP

    ' 对调铆钉孔：将第一轴线反向（hole1?hole2 互换），锚点（中点）不变
    Dim holeAxis1Local(2) As Double
    If g_swapHoles_NP Then
        holeAxis1Local(0) = -g_holeAxis1X: holeAxis1Local(1) = -g_holeAxis1Y: holeAxis1Local(2) = -g_holeAxis1Z
    Else
        holeAxis1Local(0) = g_holeAxis1X: holeAxis1Local(1) = g_holeAxis1Y: holeAxis1Local(2) = g_holeAxis1Z
    End If

    ' ── 计算旋转矩阵 R：使托板螺母的两个轴线与安装孔的两个轴线对齐 ─────────
    ' 构建托板螺母的坐标系 F1：X = g_bnAxis1, Y = g_bnAxis2, Z = cross(X, Y)
    Dim f1x(2) As Double, f1y(2) As Double, f1z(2) As Double
    f1x(0) = g_bnAxis1(0): f1x(1) = g_bnAxis1(1): f1x(2) = g_bnAxis1(2)
    f1y(0) = g_bnAxis2(0): f1y(1) = g_bnAxis2(1): f1y(2) = g_bnAxis2(2)
    ' Z = X × Y
    f1z(0) = f1x(1) * f1y(2) - f1x(2) * f1y(1)
    f1z(1) = f1x(2) * f1y(0) - f1x(0) * f1y(2)
    f1z(2) = f1x(0) * f1y(1) - f1x(1) * f1y(0)
    ' 归一化 Z 轴（理论上 X 和 Y 已经归一化且垂直，Z 应该自动归一化，但保险起见仍归一化）
    Dim f1zLen As Double
    f1zLen = Sqr(f1z(0) * f1z(0) + f1z(1) * f1z(1) + f1z(2) * f1z(2))
    If f1zLen > 0.000000000001 Then
        f1z(0) = f1z(0) / f1zLen: f1z(1) = f1z(1) / f1zLen: f1z(2) = f1z(2) / f1zLen
    End If

    ' 构建安装孔的坐标系 F2：X = holeAxis1Local, Y = holeAxis2Dir, Z = cross(X, Y)
    Dim f2x(2) As Double, f2y(2) As Double, f2z(2) As Double
    f2x(0) = holeAxis1Local(0): f2x(1) = holeAxis1Local(1): f2x(2) = holeAxis1Local(2)
    f2y(0) = holeAxis2Dir(0): f2y(1) = holeAxis2Dir(1): f2y(2) = holeAxis2Dir(2)
    ' Z = X × Y
    f2z(0) = f2x(1) * f2y(2) - f2x(2) * f2y(1)
    f2z(1) = f2x(2) * f2y(0) - f2x(0) * f2y(2)
    f2z(2) = f2x(0) * f2y(1) - f2x(1) * f2y(0)
    ' 归一化 Z 轴
    Dim f2zLen As Double
    f2zLen = Sqr(f2z(0) * f2z(0) + f2z(1) * f2z(1) + f2z(2) * f2z(2))
    If f2zLen > 0.000000000001 Then
        f2z(0) = f2z(0) / f2zLen: f2z(1) = f2z(1) / f2zLen: f2z(2) = f2z(2) / f2zLen
    End If

    ' R = F2 * F1^T（将托板螺母坐标系 F1 旋转到安装孔坐标系 F2）
    Dim R(2, 2) As Double
    Dim ri As Integer, rj As Integer
    For ri = 0 To 2
        For rj = 0 To 2
            R(ri, rj) = FrameCol_NP(ri, 0, f2x, f2y, f2z) * FrameCol_NP(rj, 0, f1x, f1y, f1z) _
                      + FrameCol_NP(ri, 1, f2x, f2y, f2z) * FrameCol_NP(rj, 1, f1x, f1y, f1z) _
                      + FrameCol_NP(ri, 2, f2x, f2y, f2z) * FrameCol_NP(rj, 2, f1x, f1y, f1z)
        Next rj
    Next ri

    ' ── 计算平移向量 ──────────────────────────────────────────────────────
    ' R * g_bnAnchorPt + translation = holeCenterLocal   =>  translation = holeCenterLocal - R * g_bnAnchorPt
    Dim rotatedAnchor(2) As Double
    rotatedAnchor(0) = R(0, 0) * g_bnAnchorPt(0) + R(0, 1) * g_bnAnchorPt(1) + R(0, 2) * g_bnAnchorPt(2)
    rotatedAnchor(1) = R(1, 0) * g_bnAnchorPt(0) + R(1, 1) * g_bnAnchorPt(1) + R(1, 2) * g_bnAnchorPt(2)
    rotatedAnchor(2) = R(2, 0) * g_bnAnchorPt(0) + R(2, 1) * g_bnAnchorPt(1) + R(2, 2) * g_bnAnchorPt(2)

    Dim translation(2) As Double
    translation(0) = holeCenterLocal(0) - rotatedAnchor(0)
    translation(1) = holeCenterLocal(1) - rotatedAnchor(1)
    translation(2) = holeCenterLocal(2) - rotatedAnchor(2)

    ' ── 添加托板螺母实例 ──────────────────────────────────────────────────
    Dim products As Object
    Set products = targetProduct_NP.products

    products.AddComponent g_nutPlateDoc.Product

    ' 最后添加的实例即为新组件
    Dim newComp As Object
    Set newComp = products.Item(products.Count)

    ' ── 通过 Position.SetComponents 设置位置（targetProduct_NP 坐标系） ─────
    ' Position.SetComponents 以 targetProduct_NP（托板螺母的父产品）为坐标系解释变换矩阵，
    ' 与 SPA 在 targetProduct_NP 为 In Work Object 时的测量坐标系一致：
    '   0-2  = targetProduct_NP 坐标系中局部 X 轴方向
    '   3-5  = targetProduct_NP 坐标系中局部 Y 轴方向
    '   6-8  = targetProduct_NP 坐标系中局部 Z 轴方向
    '   9-11 = targetProduct_NP 坐标系中原点位置
    Dim moveMatrix(11)
    moveMatrix(0) = R(0, 0)
    moveMatrix(1) = R(1, 0)
    moveMatrix(2) = R(2, 0)
    moveMatrix(3) = R(0, 1)
    moveMatrix(4) = R(1, 1)
    moveMatrix(5) = R(2, 1)
    moveMatrix(6) = R(0, 2)
    moveMatrix(7) = R(1, 2)
    moveMatrix(8) = R(2, 2)
    moveMatrix(9) = translation(0)
    moveMatrix(10) = translation(1)
    moveMatrix(11) = translation(2)

    ' ── 调试：发送给 Position.SetComponents 的矩阵（targetProduct_NP 坐标系） ──
    If DEBUG_MODE_NP Then
        MsgBox "[DEBUG] 最终定位矩阵（targetProduct_NP 坐标系）" & Chr(10) & _
               "R X轴 = (" & Round(R(0, 0), 4) & ", " & Round(R(1, 0), 4) & ", " & Round(R(2, 0), 4) & ")" & Chr(10) & _
               "R Y轴 = (" & Round(R(0, 1), 4) & ", " & Round(R(1, 1), 4) & ", " & Round(R(2, 1), 4) & ")" & Chr(10) & _
               "R Z轴 = (" & Round(R(0, 2), 4) & ", " & Round(R(1, 2), 4) & ", " & Round(R(2, 2), 4) & ")" & Chr(10) & _
               "平移  = (" & Round(translation(0), 4) & ", " & Round(translation(1), 4) & ", " & Round(translation(2), 4) & ")", _
               vbInformation, "快速装配托板螺母[DEBUG]"
    End If

    ' 说明：Position.SetComponents 直接设置组件在 targetProduct_NP 坐标系中的绝对位置。
    '       Move.Apply 是相对（增量）变换，对已有位置的组件累加变换：
    '         Dim moveObj As Object
    '         Set moveObj = newComp.Move
    '         Set moveObj = moveObj.MovableObject
    '         moveObj.Apply moveMatrix
    '       对于新添加的组件，Move.Apply 等效于绝对设置（初始位置为原点）。
    '       但对已有非零位置的组件，Move.Apply 会产生叠加，因此本宏统一使用
    '       Position.SetComponents 避免累加误差。
    newComp.Position.SetComponents moveMatrix

    ' ── 记录最近装配件信息（供翻转重装使用） ─────────────────────────────
    Set g_lastProducts_NP = products
    g_lastCompIdx_NP = products.Count
    g_count_NP = g_count_NP + 1

    ' 新装配后启用翻转/对调按钮
    g_hasLastComp_NP = True
    FlipForm_NP.btnFlip.Enabled = True
    FlipForm_NP.btnSwap.Enabled = True

    ' ── 记录到装配历史（供撤销使用） ──────────────────────────────────────
    If g_historyCount_NP < 100 Then
        Set g_assemblyHistory_NP(g_historyCount_NP, 0) = products
        g_assemblyHistory_NP(g_historyCount_NP, 1) = products.Count
        ' 保存孔的几何信息，供撤销后翻转使用
        g_assemblyHistory_NP(g_historyCount_NP, 2) = g_holeAxis1X
        g_assemblyHistory_NP(g_historyCount_NP, 3) = g_holeAxis1Y
        g_assemblyHistory_NP(g_historyCount_NP, 4) = g_holeAxis1Z
        g_assemblyHistory_NP(g_historyCount_NP, 5) = g_holeAxis2X
        g_assemblyHistory_NP(g_historyCount_NP, 6) = g_holeAxis2Y
        g_assemblyHistory_NP(g_historyCount_NP, 7) = g_holeAxis2Z
        g_assemblyHistory_NP(g_historyCount_NP, 8) = g_holePtX_NP
        g_assemblyHistory_NP(g_historyCount_NP, 9) = g_holePtY_NP
        g_assemblyHistory_NP(g_historyCount_NP, 10) = g_holePtZ_NP
        g_historyCount_NP = g_historyCount_NP + 1
        FlipForm_NP.btnUndo.Enabled = True
    End If

End Sub


' ============================================================================
' MoveLastNutPlate：在不删除/重建的情况下，将最近装配的托板螺母移动到
'   当前 g_flipDir_NP 对应的翻转位置。
' ============================================================================
Public Sub MoveLastNutPlate()

    Dim lastComp As Object
    Set lastComp = g_lastProducts_NP.Item(g_lastCompIdx_NP)

    ' ── 使用与 PlaceNutPlateAtHole 相同的逻辑重新定位 ──────────────────
    ' Move.Apply 是相对变换，无法直接设置绝对位置。
    ' Position.SetComponents 可直接设置组件在 targetProduct_NP 坐标系中的绝对位置。
    Dim holeAxis2Dir(2) As Double
    If g_flipDir_NP Then
        holeAxis2Dir(0) = -g_holeAxis2X
        holeAxis2Dir(1) = -g_holeAxis2Y
        holeAxis2Dir(2) = -g_holeAxis2Z
    Else
        holeAxis2Dir(0) = g_holeAxis2X
        holeAxis2Dir(1) = g_holeAxis2Y
        holeAxis2Dir(2) = g_holeAxis2Z
    End If

    Dim holeCenterLocal(2) As Double
    holeCenterLocal(0) = g_holePtX_NP: holeCenterLocal(1) = g_holePtY_NP: holeCenterLocal(2) = g_holePtZ_NP

    ' 对调铆钉孔：将第一轴线反向（hole1?hole2 互换），锚点（中点）不变
    Dim holeAxis1Local(2) As Double
    If g_swapHoles_NP Then
        holeAxis1Local(0) = -g_holeAxis1X: holeAxis1Local(1) = -g_holeAxis1Y: holeAxis1Local(2) = -g_holeAxis1Z
    Else
        holeAxis1Local(0) = g_holeAxis1X: holeAxis1Local(1) = g_holeAxis1Y: holeAxis1Local(2) = g_holeAxis1Z
    End If
    ' 构建托板螺母的坐标系 F1
    Dim f1x(2) As Double, f1y(2) As Double, f1z(2) As Double
    f1x(0) = g_bnAxis1(0): f1x(1) = g_bnAxis1(1): f1x(2) = g_bnAxis1(2)
    f1y(0) = g_bnAxis2(0): f1y(1) = g_bnAxis2(1): f1y(2) = g_bnAxis2(2)
    f1z(0) = f1x(1) * f1y(2) - f1x(2) * f1y(1)
    f1z(1) = f1x(2) * f1y(0) - f1x(0) * f1y(2)
    f1z(2) = f1x(0) * f1y(1) - f1x(1) * f1y(0)
    Dim f1zLen As Double
    f1zLen = Sqr(f1z(0) * f1z(0) + f1z(1) * f1z(1) + f1z(2) * f1z(2))
    If f1zLen > 0.000000000001 Then
        f1z(0) = f1z(0) / f1zLen: f1z(1) = f1z(1) / f1zLen: f1z(2) = f1z(2) / f1zLen
    End If

    ' 构建安装孔的坐标系 F2
    Dim f2x(2) As Double, f2y(2) As Double, f2z(2) As Double
    f2x(0) = holeAxis1Local(0): f2x(1) = holeAxis1Local(1): f2x(2) = holeAxis1Local(2)
    f2y(0) = holeAxis2Dir(0): f2y(1) = holeAxis2Dir(1): f2y(2) = holeAxis2Dir(2)
    f2z(0) = f2x(1) * f2y(2) - f2x(2) * f2y(1)
    f2z(1) = f2x(2) * f2y(0) - f2x(0) * f2y(2)
    f2z(2) = f2x(0) * f2y(1) - f2x(1) * f2y(0)
    Dim f2zLen As Double
    f2zLen = Sqr(f2z(0) * f2z(0) + f2z(1) * f2z(1) + f2z(2) * f2z(2))
    If f2zLen > 0.000000000001 Then
        f2z(0) = f2z(0) / f2zLen: f2z(1) = f2z(1) / f2zLen: f2z(2) = f2z(2) / f2zLen
    End If

    ' R = F2 * F1^T
    Dim R(2, 2) As Double
    Dim ri As Integer, rj As Integer
    For ri = 0 To 2
        For rj = 0 To 2
            R(ri, rj) = FrameCol_NP(ri, 0, f2x, f2y, f2z) * FrameCol_NP(rj, 0, f1x, f1y, f1z) _
                      + FrameCol_NP(ri, 1, f2x, f2y, f2z) * FrameCol_NP(rj, 1, f1x, f1y, f1z) _
                      + FrameCol_NP(ri, 2, f2x, f2y, f2z) * FrameCol_NP(rj, 2, f1x, f1y, f1z)
        Next rj
    Next ri

    Dim rotatedAnchor(2) As Double
    rotatedAnchor(0) = R(0, 0) * g_bnAnchorPt(0) + R(0, 1) * g_bnAnchorPt(1) + R(0, 2) * g_bnAnchorPt(2)
    rotatedAnchor(1) = R(1, 0) * g_bnAnchorPt(0) + R(1, 1) * g_bnAnchorPt(1) + R(1, 2) * g_bnAnchorPt(2)
    rotatedAnchor(2) = R(2, 0) * g_bnAnchorPt(0) + R(2, 1) * g_bnAnchorPt(1) + R(2, 2) * g_bnAnchorPt(2)

    Dim translation(2) As Double
    translation(0) = holeCenterLocal(0) - rotatedAnchor(0)
    translation(1) = holeCenterLocal(1) - rotatedAnchor(1)
    translation(2) = holeCenterLocal(2) - rotatedAnchor(2)

    Dim moveMatrix(11)
    moveMatrix(0) = R(0, 0): moveMatrix(1) = R(1, 0): moveMatrix(2) = R(2, 0)
    moveMatrix(3) = R(0, 1): moveMatrix(4) = R(1, 1): moveMatrix(5) = R(2, 1)
    moveMatrix(6) = R(0, 2): moveMatrix(7) = R(1, 2): moveMatrix(8) = R(2, 2)
    moveMatrix(9) = translation(0)
    moveMatrix(10) = translation(1)
    moveMatrix(11) = translation(2)

    ' 使用 Position.SetComponents 直接设置绝对位置（targetProduct_NP 坐标系），
    ' 避免 Move.Apply（相对变换）在组件已有非零位置时产生叠加误差。
    lastComp.Position.SetComponents moveMatrix

End Sub


' ============================================================================
' UndoLastNutPlate：撤销最近装配的托板螺母。
' ============================================================================
Public Sub UndoLastNutPlate()
    If g_historyCount_NP = 0 Then Exit Sub

    ' 获取最后一条历史记录
    Dim lastIdx As Long
    lastIdx = g_historyCount_NP - 1
    Dim products As Object
    Set products = g_assemblyHistory_NP(lastIdx, 0)
    Dim compIdx As Long
    compIdx = CLng(g_assemblyHistory_NP(lastIdx, 1))

    ' 删除该托板螺母
    On Error Resume Next
    products.Remove compIdx
    On Error GoTo 0

    ' 清除历史记录中的最后一项
    Set g_assemblyHistory_NP(lastIdx, 0) = Nothing
    g_assemblyHistory_NP(lastIdx, 1) = 0
    g_historyCount_NP = g_historyCount_NP - 1
    g_count_NP = g_count_NP - 1

    ' 更新状态：撤销后禁用翻转功能，直到下一次装配
    ' （翻转功能在撤销后的状态管理过于复杂，容易出错，因此撤销后禁用翻转）
    FlipForm_NP.btnUndo.Enabled = (g_historyCount_NP > 0)

    ' 撤销后禁用翻转/对调功能（下次装配时会重新启用）
    g_hasLastComp_NP = False
    FlipForm_NP.btnFlip.Enabled = False
    FlipForm_NP.btnSwap.Enabled = False

    ' 更新状态栏
    CATIA.StatusBar = "已撤销上一个托板螺母。当前已装配: " & g_count_NP & " 个 " & g_nutPlatePN
End Sub


' ============================================================================
' 辅助函数：返回坐标系 {vx, vy, vz} 第 [col] 列的第 [row] 行分量。
' ============================================================================
Private Function FrameCol_NP(ByVal row As Integer, ByVal col As Integer, _
                          ByRef vx() As Double, ByRef vy() As Double, _
                          ByRef vz() As Double) As Double
    Select Case col
        Case 0: FrameCol_NP = vx(row)
        Case 1: FrameCol_NP = vy(row)
        Case 2: FrameCol_NP = vz(row)
    End Select
End Function


' ============================================================================
' TryGetAxis_NP / TryGetCenter_NP / TryGetPoint_NP / TryGetDirection_NP / TryGetMeasurable_NP
' ============================================================================

Private Function TryGetAxis_NP(meas As Object, axArr) As Boolean
    On Error Resume Next
    Err.Clear
    meas.GetAxis axArr
    TryGetAxis_NP = (Err.Number = 0)
End Function

Private Function TryGetDirection_NP(meas As Object, dirArr) As Boolean
    On Error Resume Next
    Err.Clear
    meas.GetDirection dirArr
    TryGetDirection_NP = (Err.Number = 0)
End Function

Private Function TryGetCenter_NP(meas As Object, ptArr) As Boolean
    On Error Resume Next
    Err.Clear
    meas.GetCenter ptArr
    TryGetCenter_NP = (Err.Number = 0)
End Function

Private Function TryGetPoint_NP(meas As Object, ptArr) As Boolean
    On Error Resume Next
    Err.Clear
    meas.GetPoint ptArr
    TryGetPoint_NP = (Err.Number = 0)
End Function

' spa     : SPAWorkbench 对象
' ref     : 待测量的 Reference 对象
' measOut : 输出的 Measurable 对象（通过 ByRef 返回）
' 返回叶层零件自己坐标系中的测量值（不使用上下文）。
Private Function TryGetMeasurable_NP(spa As Object, ref As Object, _
                                  ByRef measOut As Object) As Boolean
    On Error Resume Next
    Err.Clear
    Set measOut = spa.GetMeasurable(ref)
    TryGetMeasurable_NP = (Err.Number = 0 And Not measOut Is Nothing)
End Function
