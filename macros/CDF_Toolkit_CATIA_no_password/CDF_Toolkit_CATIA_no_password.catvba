Attribute VB_Name = "A1l_CDF_Tool_2D3D"
Option Explicit
#If VBA7 Then
    ' VBA7 (Office 2010及以上，支持64位)
    Public Declare PtrSafe Function GetCursorPos Lib "user32" (lpPoint As POINTAPI) As Long
    #If Win64 Then
        Public Declare PtrSafe Function MonitorFromPoint Lib "user32" (ByVal xPoint As LongLong, ByVal yPoint As LongLong, ByVal dwFlags As Long) As LongPtr
    #Else
        Public Declare PtrSafe Function MonitorFromPoint Lib "user32" (ByVal xPoint As Long, ByVal yPoint As Long, ByVal dwFlags As Long) As LongPtr
    #End If
    Public Declare PtrSafe Function GetMonitorInfo Lib "user32" Alias "GetMonitorInfoA" (ByVal hMonitor As LongPtr, lpmi As MONITORINFO) As Long
    Public Declare PtrSafe Function SetWindowPos Lib "user32" (ByVal hwnd As LongPtr, ByVal hWndInsertAfter As LongPtr, ByVal x As Long, ByVal y As Long, ByVal cx As Long, ByVal cy As Long, ByVal wFlags As Long) As Long
    Public Declare PtrSafe Function FindWindow Lib "user32" Alias "FindWindowA" (ByVal lpClassName As String, ByVal lpWindowName As String) As LongPtr
    Public Declare PtrSafe Function GetWindowRect Lib "user32" (ByVal hwnd As LongPtr, lpRect As RECT) As Long

#Else
    ' 旧版 VBA (Office 2007及以下，仅32位)
    Public Declare Function GetCursorPos Lib "user32" (lpPoint As POINTAPI) As Long
    Public Declare Function MonitorFromPoint Lib "user32" (ByVal xPoint As Long, ByVal yPoint As Long, ByVal dwFlags As Long) As Long
    Public Declare Function GetMonitorInfo Lib "user32" Alias "GetMonitorInfoA" (ByVal hMonitor As Long, lpmi As MONITORINFO) As Long
    Public Declare Function SetWindowPos Lib "user32" (ByVal hwnd As Long, ByVal hWndInsertAfter As Long, ByVal x As Long, ByVal y As Long, ByVal cx As Long, ByVal cy As Long, ByVal wFlags As Long) As Long
    Public Declare Function FindWindow Lib "user32" Alias "FindWindowA" (ByVal lpClassName As String, ByVal lpWindowName As String) As Long
    Public Declare Function GetWindowRect Lib "user32" (ByVal hwnd As Long, lpRect As RECT) As Long

#End If

' 【关键】POINTAPI 结构体分平台定义
#If Win64 Then
    Public Type POINTAPI
        x As LongLong
        y As LongLong
    End Type
#Else
    Public Type POINTAPI
        x As Long
        y As Long
    End Type
#End If

Public Type RECT
    Left As Long
    Top As Long
    Right As Long
    Bottom As Long
End Type

Public Type MONITORINFO
    cbSize As Long
    rcMonitor As RECT
    rcWork As RECT
    dwFlags As Long
End Type
Public Const HWND_TOPMOST = -1
Public Const SWP_NOSIZE = &H1

Public Const MONITOR_DEFAULTTONULL = 0
Public Const MONITOR_DEFAULTTOPRIMARY = 1
Public Const MONITOR_DEFAULTTONEAREST = 2

Public oActDoc As Object, objExcel As Object
Public oSel As Object
'Const CATVBAPATH = "D:\CATIA_Related\CATIA-Copilot\macros\CDF_Toolkit_CATIA"

Sub CATMain()

IntCATIA


CDF_Tool.Show vbModeless
Dim hwnd As LongPtr
hwnd = FindWindow(vbNullString, CDF_Tool.Caption)
SetWindowToRightEdgeCentered hwnd

On Error Resume Next
CDF_Tool.MultiPage1.Value = 0
Select Case CATIA.GetWorkbenchId()
Case "Drw"
    CDF_Tool.MultiPage1.Value = 1
Case "LatheProgramWorkbench"
    CDF_Tool.MultiPage1.Value = 2
Case "ManufacturingProgramWorkbench"
    CDF_Tool.MultiPage1.Value = 2
Case "M3xProgramWorkbench"
    CDF_Tool.MultiPage1.Value = 2
Case "CATAMGProgramWorkbench"
    CDF_Tool.MultiPage1.Value = 2
Case "ManufacturingNCReviewWorkbench"
    CDF_Tool.MultiPage1.Value = 2
Case Else
End Select
If oActDoc Is Nothing Then
CDF_Tool.MultiPage1.Value = 0
End If

End Sub

Public Function oCATVBA_Folder(Optional ByVal sFolder As String)
    ' 动态获取当前 .catvba 文件所在目录，无硬编码路径
    ' 有参数 sFolder 则取得（或创建）与 .catvba 同目录的子目录 sFolder

    Dim oFSO As Object
    Dim CATVBA_Dir As String
    Set oFSO = CreateObject("Scripting.FileSystemObject")

    ' 通过 MSAPC 获取当前正在执行的 .catvba 项目完整路径
    On Error Resume Next
    Dim oApc As Object
    #If VBA7 Then
        Set oApc = CreateObject("MSAPC.Apc.7.1")
    #Else
        Set oApc = CreateObject("MSAPC.Apc.6.2")
    #End If
    Dim sProjectPath As String
    sProjectPath = oApc.ExecutingProject.DisplayName
    On Error GoTo 0

    If oFSO.FileExists(sProjectPath) Then
        ' 正常情况：取 .catvba 文件的父目录
        CATVBA_Dir = oFSO.GetParentFolderName(sProjectPath)
    Else
        ' 兜底：取当前活动文档的保存目录
        On Error Resume Next
        CATVBA_Dir = oFSO.GetParentFolderName(CATIA.ActiveDocument.FullName)
        On Error GoTo 0
    End If

    If sFolder <> "" Then
        CATVBA_Dir = CATVBA_Dir & "\" & sFolder
        If Not oFSO.FolderExists(CATVBA_Dir) Then
            oFSO.CreateFolder CATVBA_Dir
        End If
    End If

    Set oCATVBA_Folder = oFSO.GetFolder(CATVBA_Dir)

End Function

Public Sub IntCATIA()
    On Error Resume Next
'        Set CATIA = GetObject(CATIA.ActiveDocument.FullName, "CATIA.Application")
'        If Err.Number <> 0 Then
'            Set CATIA = CreateObject("CATIA.Application")
'        End If
  
    Set oActDoc = CATIA.ActiveDocument
    On Error GoTo 0
End Sub
Public Sub IntExcel()
    On Error Resume Next
        Set objExcel = GetObject(, "Excel.Application")
        If Err.Number <> 0 Then
            Set objExcel = CreateObject("Excel.Application")
            
        End If
    On Error GoTo 0
End Sub
Public Function DwgLinkedDoc(oDocDwg)
On Error Resume Next
    If (TypeName(oDocDwg) <> "DrawingDocument") Then
    Exit Function
    End If
    
Dim DrawingSheets1, drawingSheet1, drawingViews1, drawingViewGenerativeBehavior1

    Set DrawingSheets1 = oDocDwg.Sheets
    Set drawingSheet1 = DrawingSheets1.ActiveSheet
    Set drawingViews1 = drawingSheet1.Views
    
    Dim i As Integer
    Dim Flag As Boolean
    Flag = False
    ' This VBA Macro Developed by Charles.Tang
    ' WeChat Chtang80,CopyRight reserved
    Dim FrontViewTmp As DrawingView
    Set FrontViewTmp = drawingViews1.Item(1)
    'catViewBackground\0,  catViewFront\1,  catViewLeft\2,  catViewRight\3,  catViewTop\4,  catViewBottom\5,  catViewRear\6,  catViewAuxiliary\7,  catViewIsom\8
    If Flag = False Then
        For i = 1 To drawingViews1.Count
            If drawingViews1.Item(i).ViewType = catViewFront Then  '
            Set FrontViewTmp = drawingViews1.Item(i)
                FrontViewTmp.Activate
                Set drawingViewGenerativeBehavior1 = FrontViewTmp.GenerativeBehavior
                Set DwgLinkedDoc = drawingViewGenerativeBehavior1.Document.Parent
                    If Err.Number = 0 Then
                        Flag = True
                        Exit For
                    End If
            End If
        Next
    End If
    
    If Flag = False Then
        For i = 1 To drawingViews1.Count
            If drawingViews1.Item(i).ViewType = catViewLeft Then
            Set FrontViewTmp = drawingViews1.Item(i)
                FrontViewTmp.Activate
                Set drawingViewGenerativeBehavior1 = FrontViewTmp.GenerativeBehavior
                Set DwgLinkedDoc = drawingViewGenerativeBehavior1.Document.Parent
                    If Err.Number = 0 Then
                        Flag = True
                        Exit For
                    End If
            End If
        Next
    End If
    
    If Flag = False Then
        For i = 1 To drawingViews1.Count
            If drawingViews1.Item(i).ViewType = catViewTop Then
            Set FrontViewTmp = drawingViews1.Item(i)
                FrontViewTmp.Activate
                Set drawingViewGenerativeBehavior1 = FrontViewTmp.GenerativeBehavior
                Set DwgLinkedDoc = drawingViewGenerativeBehavior1.Document.Parent
                    If Err.Number = 0 Then
                        Flag = True
                        Exit For
                    End If
            End If
        Next
    End If
    
    If Flag = False Then
        For i = 1 To drawingViews1.Count
            If drawingViews1.Item(i).ViewType = catViewIsom Then
            Set FrontViewTmp = drawingViews1.Item(i)
                FrontViewTmp.Activate
                Set drawingViewGenerativeBehavior1 = FrontViewTmp.GenerativeBehavior
                Set DwgLinkedDoc = drawingViewGenerativeBehavior1.Document.Parent
                    If Err.Number = 0 Then
                        Flag = True
                        Exit For
                    End If
            End If
        Next
    End If
    
    If Flag = False Then
        For i = 1 To drawingViews1.Count
            If drawingViews1.Item(i).ViewType = catViewRight Then
            Set FrontViewTmp = drawingViews1.Item(i)
                FrontViewTmp.Activate
                Set drawingViewGenerativeBehavior1 = FrontViewTmp.GenerativeBehavior
                Set DwgLinkedDoc = drawingViewGenerativeBehavior1.Document.Parent
                    If Err.Number = 0 Then
                        Flag = True
                        Exit For
                    End If
            End If
        Next
    End If
    
    If Flag = False Then
        For i = 1 To drawingViews1.Count
            If drawingViews1.Item(i).ViewType = catViewBottom Then
            Set FrontViewTmp = drawingViews1.Item(i)
                FrontViewTmp.Activate
                Set drawingViewGenerativeBehavior1 = FrontViewTmp.GenerativeBehavior
                Set DwgLinkedDoc = drawingViewGenerativeBehavior1.Document.Parent
                    If Err.Number = 0 Then
                        Flag = True
                        Exit For
                    End If
            End If
        Next
    End If

    If Flag = False Then
        For i = 1 To drawingViews1.Count
            If drawingViews1.Item(i).ViewType = catViewRear Then
            Set FrontViewTmp = drawingViews1.Item(i)
                FrontViewTmp.Activate
                Set drawingViewGenerativeBehavior1 = FrontViewTmp.GenerativeBehavior
                Set DwgLinkedDoc = drawingViewGenerativeBehavior1.Document.Parent
                    If Err.Number = 0 Then
                        Flag = True
                        Exit For
                    End If
            End If
        Next
    End If
    
    
    Set DrawingSheets1 = Nothing
    Set drawingSheet1 = Nothing
    Set drawingViews1 = Nothing
    Set FrontViewTmp = Nothing
    Set drawingViewGenerativeBehavior1 = Nothing
On Error GoTo 0
End Function
' 改造后的通用子程序：设置任意窗口到鼠标所在显示器右侧垂直居中
Sub SetWindowToRightEdgeCentered(ByVal hwnd As LongPtr)
    Dim pt As POINTAPI
    Dim hMonitor As LongPtr
    Dim mi As MONITORINFO
    Dim formWidth As Long
    Dim formHeight As Long
    
    ' 1. 获取鼠标位置
    GetCursorPos pt
    ' 2. 获取鼠标所在显示器句柄
    hMonitor = MonitorFromPoint(pt.x, pt.y, MONITOR_DEFAULTTONEAREST)
    ' 3. 获取显示器信息
    mi.cbSize = Len(mi)
    GetMonitorInfo hMonitor, mi
    
    ' 4. 通用获取窗口宽高（替代Form1.Width/Height，无硬编码）
    GetWindowSize hwnd, formWidth, formHeight
    
    ' 5. 计算窗口位置
    Dim PosX As Long
    Dim PosY As Long
    PosX = mi.rcMonitor.Right - formWidth
    PosY = mi.rcMonitor.Bottom - formHeight - 50  ' 保持原垂直位置逻辑
    
    ' 6. 设置窗口位置
    SetWindowPos hwnd, HWND_TOPMOST, PosX, PosY, 0, 0, SWP_NOSIZE
End Sub
Private Sub GetWindowSize(ByVal hwnd As LongPtr, ByRef width As Long, ByRef height As Long)
    Dim RECT As RECT
    ' 通过API获取窗口的屏幕矩形（替代Form1.Width/Height）
    GetWindowRect hwnd, RECT
    width = RECT.Right - RECT.Left
    height = RECT.Bottom - RECT.Top
End Sub

Attribute VB_Name = "Add_Properties_3D"
Option Explicit

Const exeprg = "Add_Properties_3D.exe"

Sub CATMain()
On Error Resume Next
Shell oCATVBA_Folder.Path & "\" & exeprg, vbNormalFocus
If Err.Number <> 0 Then
MsgBox "无法调用" & exeprg & vbCrLf & "请确认" & exeprg & "存在于" & oCATVBA_Folder.Path, vbQuestion, "CATIA工具箱"
End If
End Sub

Attribute VB_Name = "AutoDrw_2D_3D"
Option Explicit
Const exeprg = "AutoDrw.exe"

Sub CATMain()
On Error Resume Next
Shell oCATVBA_Folder.Path & "\" & exeprg, vbNormalFocus
If Err.Number <> 0 Then
MsgBox "无法调用" & exeprg & vbCrLf & "请确认" & exeprg & "存在于" & oCATVBA_Folder.Path, vbQuestion, "CATIA工具箱"
End If
End Sub

Attribute VB_Name = "Batch_Print_2D3D"
Option Explicit

Const exeprg = "Batch_Print_2D3D.exe"
Sub CATMain()
On Error Resume Next
Shell oCATVBA_Folder.Path & "\" & exeprg, vbNormalFocus
If Err.Number <> 0 Then
MsgBox "无法调用" & exeprg & vbCrLf & "请确认" & exeprg & "存在于" & oCATVBA_Folder.Path, vbQuestion, "CATIA工具箱"
End If
End Sub

Attribute VB_Name = "Batch_Rename_3D"
Option Explicit

Const exeprg = "Batch_Rename_3D.exe"

Sub CATMain()
On Error Resume Next
Shell oCATVBA_Folder.Path & "\" & exeprg, vbNormalFocus
If Err.Number <> 0 Then
MsgBox "无法调用" & exeprg & vbCrLf & "请确认" & exeprg & "存在于" & oCATVBA_Folder.Path, vbQuestion, "CATIA工具箱"
End If
End Sub

Attribute VB_Name = "Body_Color_3D"
Option Explicit

Const exeprg = "Body_Color_3D.exe"

Sub CATMain()
On Error Resume Next
Shell oCATVBA_Folder.Path & "\" & exeprg, vbNormalFocus
If Err.Number <> 0 Then
MsgBox "无法调用" & exeprg & vbCrLf & "请确认" & exeprg & "存在于" & oCATVBA_Folder.Path, vbQuestion, "CATIA工具箱"
End If
End Sub

Attribute VB_Name = "Body_Hide_3D"
Option Explicit

Const exeprg = "Body_Hide_3D.exe"

Sub CATMain()
On Error Resume Next
Shell oCATVBA_Folder.Path & "\" & exeprg, vbNormalFocus
If Err.Number <> 0 Then
MsgBox "无法调用" & exeprg & vbCrLf & "请确认" & exeprg & "存在于" & oCATVBA_Folder.Path, vbQuestion, "CATIA工具箱"
End If
End Sub

Attribute VB_Name = "Body_ShowAll_3D"
Option Explicit

Const exeprg = "Body_ShowAll_3D.exe"

Sub CATMain()
On Error Resume Next
Shell oCATVBA_Folder.Path & "\" & exeprg, vbNormalFocus
If Err.Number <> 0 Then
MsgBox "无法调用" & exeprg & vbCrLf & "请确认" & exeprg & "存在于" & oCATVBA_Folder.Path, vbQuestion, "CATIA工具箱"
End If
End Sub

Attribute VB_Name = "Body_ShowReverse_3D"
Option Explicit

Const exeprg = "Body_ShowReverse_3D.exe"

Sub CATMain()
On Error Resume Next
Shell oCATVBA_Folder.Path & "\" & exeprg, vbNormalFocus
If Err.Number <> 0 Then
MsgBox "无法调用" & exeprg & vbCrLf & "请确认" & exeprg & "存在于" & oCATVBA_Folder.Path, vbQuestion, "CATIA工具箱"
End If
End Sub

Attribute VB_Name = "CDF_Tool"
Attribute VB_Base = "0{5D2F2ACE-4869-469C-8850-149E27C514E7}{7C1C534B-4770-4287-9361-7CF83C05E4CA}"
Attribute VB_GlobalNameSpace = False
Attribute VB_Creatable = False
Attribute VB_PredeclaredId = True
Attribute VB_Exposed = False
Attribute VB_TemplateDerived = False
Attribute VB_Customizable = False
Option Explicit

Private Sub cmdClearData_Click()
ClearUselessData_3D.CATMain
End Sub

Private Sub cmdComp2Prod_Click()
Component2Product_3D.CATMain
End Sub

Private Sub cmdExpPro_Click()
Export_Properties_3D.CATMain
End Sub

Private Sub cmdGearRack_Click()
Gear_And_Rack_3D.CATMain
End Sub

Private Sub cmdPartBodiesReOrder_Click()
PartBodiesReOrder_3D.CATMain
End Sub
Private Sub BatchRename_Click()
Batch_Rename_3D.CATMain
End Sub

Private Sub cmdActRenameNumber_Click()
CNC_ReNumberAct.CATMain
End Sub

Private Sub cmdAutoDrw_Click()
AutoDrw_2D_3D.CATMain
Unload CDF_Tool
End Sub

Private Sub cmdBatchPrint_Click()
Batch_Print_2D3D.CATMain
End Sub

Private Sub cmdBatchPrt_Click()
Batch_Print_2D3D.CATMain
End Sub

Private Sub cmdCaptureImage_Click()
Capture_Image_3D.CATMain
End Sub

Private Sub cmdCNCTools_Click()
CNC_Prog_List2.CATMain
End Sub

Private Sub cmdColorShow_Click()
Body_Color_3D.CATMain
End Sub

Private Sub cmdDimensionTag_Click()
Dimension_Tag_2D.CATMain
End Sub

Private Sub cmdDrwAuto_Click()
MsgBox "此功能需要 AutoDrw_Reg.exe，当前版本不包含此组件。", vbInformation, "CATIA工具箱"
End Sub

Private Sub cmdDrwLink_Click()
Change_Link_2D.CATMain
End Sub

Private Sub cmdExportPDF_Click()
IntCATIA
ExportPDF oActDoc
End Sub

Private Sub cmdExportSTP2_Click()
Export_Stp2_2D3D.CATMain
End Sub

Private Sub cmdExportTable_Click()
Table_2_Excel_2D.CATMain
End Sub

Private Sub cmdFastHole_Click()
FastHole_3D.CATMain
End Sub

Private Sub cmdFix_Click()
Fix_Unfix_Position_3D.CATMain
End Sub

Private Sub cmdGBstyle_Click()
View_Name_GB_2D.CATMain
End Sub

Private Sub cmdGraphReOrder_Click()
Graph_ReOrder_3D.CATMain
End Sub

Private Sub cmdGrid_Click()
Draw_Cor_Grid_2D.CATMain
End Sub

Private Sub cmdInsertDrw_Click()
Insert_GB_Frame_3D.CATMain
End Sub

Private Sub cmdNewfrmTemplate_Click()
New_From_Template.CATMain
End Sub

Private Sub cmdOpenCurrentFd_Click()
Open_Current_Folder.CATMain
End Sub

Private Sub cmdOpenCurrentFolder_Click()
Open_Current_Folder.CATMain
End Sub

Private Sub cmdOpenModelDrafting_Click()
Open_Drawing_Model_3D.CATMain
End Sub

Private Sub cmdOpenModelDwg_Click()
Open_Drawing_Model_3D.CATMain
End Sub



Private Sub cmdPrgList_Click()
MsgBox "此功能需要 CNCTools_Reg.exe，当前版本不包含此组件。", vbInformation, "CATIA工具箱"
End Sub

Private Sub cmdPrgListExcel_Click()
CNC_Prog_List.CATMain
End Sub

Private Sub cmdPrjPlane_Click()
Modify_Proj_Plane_2D.CATMain
End Sub



Private Sub cmdReg_Click()
MsgBox "此功能需要 Reg.exe，当前版本不包含此组件。", vbInformation, "CATIA工具箱"
End Sub

Private Sub cmdSelDims_Click()
Select_Dims_2D.CATMain
End Sub

Private Sub cmdTable_Click()
Table_2_Excel_2D.CATMain
End Sub

Private Sub cmdTextOnFace_Click()
TextOnPlanarFace_3D.CATMain
End Sub

Private Sub cmdWrkFolder_Click()
Open_Current_Folder.CATMain
End Sub

Private Sub cmdZipPDFSTP_Click()
Export_Zipped_PDF_STP_2D.CATMain
End Sub

Private Sub CommandButton2_Click()
Open_Current_Folder.CATMain
End Sub

Private Sub Export_BOM2_Click()
Exact_BOM_3D.CATMain
'Unload CDF_Tool
End Sub

Private Sub Label6_Click()
Shell "explorer.exe https://" & Label6.Caption, vbNormalFocus
End Sub

Private Sub MultiPage1_Change()
Select Case MultiPage1.Value
Case 0
MultiPage1.height = 500
Case 1
MultiPage1.height = 405
Case 2
MultiPage1.height = 226
Case 3
MultiPage1.height = 486
Case Else
End Select
Me.height = MultiPage1.height + 26
Me.width = MultiPage1.width + 10
End Sub

Private Sub NC_Prog_ReName_Click()
MP_ReName_Export_3D.CATMain
End Sub

Private Sub Properties_Click()
Add_Properties_3D.CATMain
End Sub

Private Sub Export_PDF_Click()
IntCATIA
ExportPDF oActDoc
End Sub

Private Sub Export_STP_Click()
IntCATIA
ExportStp oActDoc
End Sub

Private Sub Inport_GB_Frame_Click()
Insert_GB_Frame_3D.CATMain
'Unload CDF_Tool
End Sub

Private Sub Part_2_Product_Click()
Part_2_Product_3D.CATMain
End Sub


'*******************************************************************
'*******************************************************************

Sub ExportPDF(oDocPDF, Optional ByVal sPath As String = "") 'sPath为输出目录，不带“\”
On Error Resume Next
Dim sName
If oDocPDF.Saved = False Then
   If MsgBox("要保存修改么?", vbYesNo) = vbYes Then
    oDocPDF.Save
   End If
End If

If (TypeName(oDocPDF) <> "DrawingDocument") Then
    MsgBox "此命令只能在工程制图模块中运行", vbInformation, "Information"
    Exit Sub
End If
Dim settingControllers1 'As SettingControllers
Dim settingRepository1 'As SettingRepository
Dim tempB
Set settingControllers1 = CATIA.SettingControllers
Set settingRepository1 = settingControllers1.Item("DraftingOptions")
tempB = settingRepository1.GetAttr("DimDesignMode")
'msgbox tempB
settingRepository1.PutAttr "DimDesignMode", False
'msgbox settingRepository1.GetAttr("DimDesignMode")
settingRepository1.Commit
If sPath = "" Then
    sName = oDocPDF.Path & "\" & Replace(oDocPDF.Name, ".", "_")
Else
   sName = sPath & "\" & Replace(oDocPDF.Name, ".", "_")
End If
    oDocPDF.ExportData sName, "pdf"
    
settingRepository1.PutAttr "DimDesignMode", tempB
settingRepository1.Commit
On Error GoTo 0
End Sub

Sub ExportStp(oDocStp, Optional ByVal sPath As String = "") 'sPath为输出目录，不带“\”
On Error Resume Next
Dim sName
If oDocStp.Saved = False Then
   If MsgBox("要保存修改么?", vbYesNo) = vbYes Then
    oDocStp.Save
    End If
End If
'*****************************
Dim settingControllers1 As Object
Dim stepSettingAtt1 As Object
Dim short1

Set settingControllers1 = CATIA.SettingControllers
Set stepSettingAtt1 = settingControllers1.Item("CATSdeStepSettingCtrl")
short1 = stepSettingAtt1.AttAP
'Debug.Print stepSettingAtt1.AttAP
If short1 <> 2 Then
stepSettingAtt1.AttAP = 2
'Debug.Print stepSettingAtt1.AttAP
End If

If (TypeName(oDocStp) = "PartDocument") Or (TypeName(oDocStp) = "ProductDocument") Then
    If sPath = "" Then
    sName = oDocStp.Path & "\" & Replace(oDocStp.Name, ".", "_")
    Else
    sName = sPath & "\" & Replace(oDocStp.Name, ".", "_")
    End If
    oDocStp.ExportData sName, "stp"
End If

If (TypeName(oDocStp) = "DrawingDocument") Then
    Dim oDocStp1
    Set oDocStp1 = DwgLinkedDoc(oDocStp)
    If sPath = "" Then
    sName = oDocStp1.Path & "\" & Replace(oDocStp1.Name, ".", "_")
    Else
    sName = sPath & "\" & Replace(oDocStp1.Name, ".", "_")
    End If
    oDocStp1.ExportData sName, "stp"
End If
stepSettingAtt1.AttAP = short1
'Debug.Print stepSettingAtt1.AttAP
Set settingControllers1 = Nothing
Set stepSettingAtt1 = Nothing
On Error GoTo 0
End Sub






'View must parallel to system aixes,view angle 0deg,90deg and -90deg

Sub Draw_Grid(oDocDrw)

If TypeName(oDocDrw) <> "DrawingDocument" Then
    MsgBox "此命令只能在工程制图模块下运行!"
    Exit Sub
End If


CATIA.RefreshDisplay = False
Dim sStatus As String

    ' Set the CATIA popup file alerts to False
    ' It prevents to stop the macro at each alert during its execution
CATIA.DisplayFileAlerts = False

    ' Optional: allows to find the sample wherever it's installed
  
    ' Variables declaration
    Dim oDrwDocument As DrawingDocument
    Set oDrwDocument = oDocDrw
    
    Dim oDrwSheets As DrawingSheets
    Dim oDrwSheet As DrawingSheet
    Dim oDrwView As DrawingView
    Dim oFactory2D ' As Factory2D
   
   ' The Distance between the lines
    Dim d As Integer
    Dim nx As Integer
    Dim ny As Integer

   ' The point coordinate select from Drawing
    Dim x1 As Integer
    Dim y1 As Integer
    Dim x2 As Integer
    Dim y2 As Integer
    Dim Pt1 'As Point2D
    Dim Pt2 'As Point2D
    
   'The view scale dAngle for rotate view scale for view scale
    Dim dScale, dAngle As Double
  
    'The view coordinate origin
    Dim x, y As Integer
    On Error Resume Next
    d = InputBox("准备工作:" & vbCrLf & "请激活需要添加百格线的视图并预先定义两点以确定百格线绘制范围" & vbCrLf & "点1为绘制区左下角" & vbCrLf & "点2为绘制区右上角" & vbCrLf & vbCrLf & "完成准备工作后再输入间距否则请先关闭此对话框" & vbCrLf & vbCrLf & "请输入间距：", "input box", "100")
    d = CInt(d)
    If Err.Number <> 0 Then
    Exit Sub
    End If
       

    Set oDrwSheets = oDrwDocument.Sheets
    Set oDrwSheet = oDrwSheets.ActiveSheet
    Set oDrwView = oDrwSheet.Views.ActiveView
    Set oFactory2D = oDrwView.Factory2D
  
    'Retrive the value of the view
     x = oDrwView.xAxisData
     y = oDrwView.yAxisData
     dScale = oDrwView.Scale
     dAngle = oDrwView.Angle
     

   'Get the coordinate from the select two point
    'On Error Resume Next

     Set oSel = oDocDrw.Selection
     oSel.Clear

     ReDim sFilter(0)
     sFilter(0) = "Point2D"
     MsgBox "请选择点 1 以定义绘制区左下角 "
     sStatus = oSel.SelectElement2(sFilter, "请选择点 1 以定义绘制区左下角", False)
     If (sStatus = "Normal") Then

      Dim SelectedPoint1
      Set SelectedPoint1 = oSel.Item(1)

      Dim pt1Coord(2)
      SelectedPoint1.GetCoordinates pt1Coord
      'MsgBox "The frst point has been selected "

      Else: MsgBox "你未选择绘制区顶点,程序退出"
      Exit Sub
      End If

      MsgBox "请选择点 2 以定义绘制区右上角 "
      sStatus = oSel.SelectElement2(sFilter, "请选择点 2 以定义绘制区右上角", False)
      If (sStatus = "Normal") Then

       Dim SelectedPoint2

       Set SelectedPoint2 = oSel.Item(1)

      Dim pt2Coord(2)
    SelectedPoint2.GetCoordinates pt2Coord
     'MsgBox "The second point has been selected "

     Else: MsgBox "你未选择完成绘制区顶点,程序退出"
     Exit Sub
     End If
   
  If dAngle = 0 Then
   x1 = CInt((pt1Coord(0) - x) / dScale)
   y1 = CInt((pt1Coord(1) - y) / dScale)
   x2 = CInt((pt2Coord(0) - x) / dScale)
   y2 = CInt((pt2Coord(1) - y) / dScale)
  End If
   If dAngle > 0 Then
     x1 = CInt((pt1Coord(1) - y) / dScale)
    y1 = CInt((pt1Coord(0) - x) / dScale)
    x2 = CInt((pt2Coord(1) - y) / dScale)
    y2 = CInt((pt2Coord(0) - x) / dScale)
  End If
 
  If dAngle < 0 Then
     x1 = CInt((pt1Coord(1) - y) / dScale)
    y1 = CInt((pt1Coord(0) - x) / dScale)
    x2 = CInt((pt2Coord(1) - y) / dScale)
    y2 = CInt((pt2Coord(0) - x) / dScale)
  End If

    x1 = d * CInt(x1 / d)
    y1 = d * CInt(y1 / d)
    x2 = d * CInt(x2 / d)
    y2 = d * CInt(y2 / d)
    
    nx = (x2 - x1) \ d 'The number of the horizontal line
    ny = (y2 - y1) \ d 'The number of the vertical  line
    

    Dim line2D1 ' As Line2D
    Dim Circle2D1 'As Circle2D
   Dim MyText As DrawingText
   Dim iFontSize As Double
   
    Dim i, j, R
   
    iFontSize = 3.5
    R = 6
    R = R / dScale

'------------------------------------------------------
Dim Di_H, Di_V
Dim Text_XYZ_H As String
Dim Text_XYZ_V As String

Di_H = 1
Di_V = 1

'Compare the drawing view HV with 3D Aixes
'Dim XX1, YY1, ZZ1, XX2, YY2, ZZ2 'As Integer
Dim XX1 As Double
Dim YY1 As Double
Dim ZZ1 As Double
Dim XX2 As Double
Dim YY2 As Double
Dim ZZ2 As Double

oDrwView.GenerativeBehavior.GetProjectionPlane XX1, YY1, ZZ1, XX2, YY2, ZZ2
MsgBox "XX1=" & XX1 & "  /YY1=" & YY1 & "  /ZZ1=" & ZZ1 & vbCrLf & "XX2=" & XX2 & "  /YY2=" & YY2 & "  /ZZ2=" & ZZ2


If (XX1 = 1) Then
    Text_XYZ_H = "X"
End If
If (XX1 = -1) Then
    Text_XYZ_H = "X"
    Di_H = -1
End If

If (YY1 = 1) Then
    Text_XYZ_H = "Y"
End If
If (YY1 = -1) Then
    Text_XYZ_H = "Y"
    Di_H = -1
End If

If (ZZ1 = 1) Then
    Text_XYZ_H = "Z"
End If
If (ZZ1 = -1) Then
    Text_XYZ_H = "Z"
    Di_H = -1
End If


If (XX2 = 1) Then
    Text_XYZ_V = "X"
End If
If (XX2 = -1) Then
    Text_XYZ_V = "X"
    Di_V = -1
End If

If (YY2 = 1) Then
    Text_XYZ_V = "Y"
End If
If (YY2 = -1) Then
    Text_XYZ_V = "Y"
    Di_V = -1
End If

If (ZZ2 = 1) Then
    Text_XYZ_V = "Z"
End If
If (ZZ2 = -1) Then
    Text_XYZ_V = "Z"
    Di_V = -1
End If

If dAngle > 0 Then
    Di_V = -Di_V
End If
If dAngle < 0 Then
    Di_H = -Di_H
End If

Dim oVisProps As VisPropertyset
oSel.Clear

Dim TextV
TextV = R / 2

 'Draw the  horizontall line

    For i = 0 To ny
      If dAngle = 0 Then
          Set line2D1 = oFactory2D.CreateLine(x1 - d / 3, y1 + d * i, x1 + nx * d + d / 3, y1 + d * i)
          oSel.Add line2D1
          Set Circle2D1 = oFactory2D.CreateClosedCircle(x1 - d / 3 - R, y1 + d * i, R)
          oSel.Add Circle2D1
          Set line2D1 = oFactory2D.CreateLine(x1 - d / 3 - R * 2, y1 + d * i, x1 - d / 3, y1 + d * i)
          oSel.Add line2D1
          Set MyText = oDrwView.Texts.Add(Text_XYZ_V, x1 - d / 3 - R, y1 + d * i + TextV)
         MyText.AnchorPosition = catMiddleCenter
         MyText.SetFontSize 0, 0, iFontSize
          Set MyText = oDrwView.Texts.Add((y1 + d * i) * Di_V, x1 - d / 3 - R, y1 + d * i - TextV)
          MyText.AnchorPosition = catMiddleCenter
          MyText.SetFontSize 0, 0, iFontSize
       End If

      If dAngle > 0 Then
          Set line2D1 = oFactory2D.CreateLine(x1 - d / 3, -y1 - d * i, x1 + nx * d + d / 3, -y1 - d * i)
          oSel.Add line2D1
          Set Circle2D1 = oFactory2D.CreateClosedCircle(x1 + nx * d + d / 3 + R, -y1 - d * i, R)
          oSel.Add Circle2D1
          Set line2D1 = oFactory2D.CreateLine(x1 + nx * d + d / 3 + R, -y1 - d * i + R, x1 + nx * d + d / 3 + R, -y1 - d * i - R)
          oSel.Add line2D1
          Set MyText = oDrwView.Texts.Add(Text_XYZ_V, x1 + nx * d + d / 3 + R + TextV, -y1 - d * i)
          MyText.AnchorPosition = catMiddleCenter
          MyText.SetFontSize 0, 0, iFontSize
          Set MyText = oDrwView.Texts.Add((y1 + d * i) * Di_V, x1 + nx * d + d / 3 + R - TextV, -y1 - d * i)
          MyText.AnchorPosition = catMiddleCenter
          MyText.SetFontSize 0, 0, iFontSize
       End If

      If dAngle < 0 Then
          Set line2D1 = oFactory2D.CreateLine(-x1 + d / 3, y1 + d * i, -(x1 + nx * d + d / 3), y1 + d * i)
          oSel.Add line2D1
          Set Circle2D1 = oFactory2D.CreateClosedCircle(-(x1 + nx * d + d / 3) - R, y1 + d * i, R)
          oSel.Add Circle2D1
          Set line2D1 = oFactory2D.CreateLine(-x1 - nx * d - d / 3 - R, y1 + d * i + R, -x1 - nx * d - d / 3 - R, y1 + d * i - R)
          oSel.Add line2D1
          Set MyText = oDrwView.Texts.Add(Text_XYZ_V, -x1 - nx * d - d / 3 - R + TextV, y1 + d * i)
          MyText.AnchorPosition = catMiddleCenter
          MyText.SetFontSize 0, 0, iFontSize
          Set MyText = oDrwView.Texts.Add((y1 + d * i) * Di_V, -x1 - nx * d - d / 3 - R - TextV, y1 + d * i)
          MyText.AnchorPosition = catMiddleCenter
         MyText.SetFontSize 0, 0, iFontSize
       End If

    Next


    
  'Draw the vertical  line
    For j = 0 To nx
      If dAngle = 0 Then
          Set line2D1 = oFactory2D.CreateLine(x1 + d * j, y1 - d / 3, x1 + d * j, y1 + ny * d + d / 3)
          oSel.Add line2D1
          Set Circle2D1 = oFactory2D.CreateClosedCircle(x1 + d * j, y1 + ny * d + d / 3 + R, R)
          oSel.Add Circle2D1
          Set line2D1 = oFactory2D.CreateLine(x1 + d * j - R, y1 + ny * d + d / 3 + R, x1 + d * j + R, y1 + ny * d + d / 3 + R)
          oSel.Add line2D1
           Set MyText = oDrwView.Texts.Add(Text_XYZ_H, x1 + d * j, y1 + ny * d + d / 3 + R + TextV)
                 MyText.AnchorPosition = catMiddleCenter
                 MyText.SetFontSize 0, 0, iFontSize
           Set MyText = oDrwView.Texts.Add((x1 + d * j) * Di_H, x1 + d * j, y1 + ny * d + d / 3 + R - TextV)
                 MyText.AnchorPosition = catMiddleCenter
                 MyText.SetFontSize 0, 0, iFontSize
      End If

      If dAngle > 0 Then
          Set line2D1 = oFactory2D.CreateLine(x1 + d * j, -y1 + d / 3, x1 + d * j, -y1 - ny * d - d / 3)
          oSel.Add line2D1
          Set Circle2D1 = oFactory2D.CreateClosedCircle(x1 + d * j, -y1 + d / 3 + R, R)
          oSel.Add Circle2D1
          Set line2D1 = oFactory2D.CreateLine(x1 + d * j, -y1 + d / 3 + R * 2, x1 + d * j, -y1 + d / 3)
          oSel.Add line2D1
           Set MyText = oDrwView.Texts.Add(Text_XYZ_H, x1 + d * j + TextV, -y1 + d / 3 + R)
                 MyText.AnchorPosition = catMiddleCenter
                 MyText.SetFontSize 0, 0, iFontSize
           Set MyText = oDrwView.Texts.Add((x1 + d * j) * Di_H, x1 + d * j - TextV, -y1 + d / 3 + R)
                 MyText.AnchorPosition = catMiddleCenter
                 MyText.SetFontSize 0, 0, iFontSize
      End If

      If dAngle < 0 Then
          Set line2D1 = oFactory2D.CreateLine(-x1 - d * j, y1 - d / 3, -x1 - d * j, y1 + ny * d + d / 3)
          oSel.Add line2D1
          Set Circle2D1 = oFactory2D.CreateClosedCircle(-x1 - d * j, y1 - d / 3 - R, R)
          oSel.Add Circle2D1
          Set line2D1 = oFactory2D.CreateLine(-x1 - d * j, y1 - d / 3 - R * 2, -x1 - d * j, y1 - d / 3)
          oSel.Add line2D1
           Set MyText = oDrwView.Texts.Add(Text_XYZ_H, -x1 - d * j + TextV, y1 - d / 3 - R)
                 MyText.AnchorPosition = catMiddleCenter
                 MyText.SetFontSize 0, 0, iFontSize
           Set MyText = oDrwView.Texts.Add((x1 + d * j) * Di_H, -x1 - d * j - TextV, y1 - d / 3 - R)
                 MyText.AnchorPosition = catMiddleCenter
                 MyText.SetFontSize 0, 0, iFontSize
      End If

   Next
Dim oFontSize As Long
  ' MyText.SetFontSize 0,  0, iFontSize
    Set oVisProps = oSel.VisProperties
    oVisProps.SetRealWidth 1, 0 '1st parameter line width 1-63 2nd parameter inheritance flag 1 or 0
    oVisProps.SetRealColor 0, 255, 0, 1

    Set oVisProps = Nothing
    Set oSel = Nothing
   


    ' Update drawing table modifications

    CATIA.ActiveWindow.ActiveViewer.Reframe
    
End Sub


Private Sub Send2SubFolder_Click()
Send_2_SubFolder_3D.CATMain
End Sub

Private Sub UserForm_Initialize()
End Sub

Attribute VB_Name = "CNC_Prog_List"
Option Explicit

Const exeprg = "CNC_Prog_List.exe"

Sub CATMain()
On Error Resume Next
Shell oCATVBA_Folder.Path & "\" & exeprg, vbNormalFocus
If Err.Number <> 0 Then
MsgBox "无法调用" & exeprg & vbCrLf & "请确认" & exeprg & "存在于" & oCATVBA_Folder.Path, vbQuestion, "CATIA工具箱"
End If
End Sub

Attribute VB_Name = "CNC_Prog_List2"
Option Explicit

Const exeprg = "CNCTools.exe"
Sub CATMain()
On Error Resume Next
Shell oCATVBA_Folder.Path & "\" & exeprg, vbNormalFocus
If Err.Number <> 0 Then
MsgBox "无法调用" & exeprg & vbCrLf & "请确认" & exeprg & "存在于" & oCATVBA_Folder.Path, vbQuestion, "CATIA工具箱"
End If
End Sub

Attribute VB_Name = "CNC_ReNumberAct"
Option Explicit

Const exeprg = "CNC_ReNumberAct.exe"

Sub CATMain()
On Error Resume Next
Shell oCATVBA_Folder.Path & "\" & exeprg, vbNormalFocus
If Err.Number <> 0 Then
MsgBox "无法调用" & exeprg & vbCrLf & "请确认" & exeprg & "存在于" & oCATVBA_Folder.Path, vbQuestion, "CATIA工具箱"
End If
End Sub

Attribute VB_Name = "Capture_Image_3D"
Option Explicit

Const exeprg = "Capture_Image_3D.exe"

Sub CATMain()
On Error Resume Next
Shell oCATVBA_Folder.Path & "\" & exeprg, vbNormalFocus
If Err.Number <> 0 Then
MsgBox "无法调用" & exeprg & vbCrLf & "请确认" & exeprg & "存在于" & oCATVBA_Folder.Path, vbQuestion, "CATIA工具箱"
End If
End Sub

Attribute VB_Name = "Change_Link_2D"
Option Explicit

Const exeprg = "Change_Link_2D.exe"
Sub CATMain()
On Error Resume Next
Shell oCATVBA_Folder.Path & "\" & exeprg, vbNormalFocus
If Err.Number <> 0 Then
MsgBox "无法调用" & exeprg & vbCrLf & "请确认" & exeprg & "存在于" & oCATVBA_Folder.Path, vbQuestion, "CATIA工具箱"
End If
End Sub

Attribute VB_Name = "ClearUselessData_3D"
Option Explicit

Const exeprg = "ClearUselessData_3D.exe"
Sub CATMain()
On Error Resume Next
Shell oCATVBA_Folder.Path & "\" & exeprg, vbNormalFocus
If Err.Number <> 0 Then
MsgBox "无法调用" & exeprg & vbCrLf & "请确认" & exeprg & "存在于" & oCATVBA_Folder.Path, vbQuestion, "CATIA工具箱"
End If
End Sub

Attribute VB_Name = "Component2Product_3D"
Option Explicit
Const exeprg = "Component2Product_3D.exe"

Sub CATMain()
On Error Resume Next
Shell oCATVBA_Folder.Path & "\" & exeprg, vbNormalFocus
If Err.Number <> 0 Then
MsgBox "无法调用" & exeprg & vbCrLf & "请确认" & exeprg & "存在于" & oCATVBA_Folder.Path, vbQuestion, "CATIA工具箱"
End If
End Sub

Attribute VB_Name = "Dimension_Tag_2D"
Option Explicit

Const exeprg = "Dimension_Tag_2D.exe"

Sub CATMain()
On Error Resume Next
Shell oCATVBA_Folder.Path & "\" & exeprg, vbNormalFocus
If Err.Number <> 0 Then
MsgBox "无法调用" & exeprg & vbCrLf & "请确认" & exeprg & "存在于" & oCATVBA_Folder.Path, vbQuestion, "CATIA工具箱"
End If
End Sub

Attribute VB_Name = "Draw_Cor_Grid_2D"
Option Explicit

Const exeprg = "Draw_Cor_Grid_2D.exe"

Sub CATMain()
On Error Resume Next
Shell oCATVBA_Folder.Path & "\" & exeprg, vbNormalFocus
If Err.Number <> 0 Then
MsgBox "无法调用" & exeprg & vbCrLf & "请确认" & exeprg & "存在于" & oCATVBA_Folder.Path, vbQuestion, "CATIA工具箱"
End If
End Sub

Attribute VB_Name = "Exact_BOM_3D"
Option Explicit

Const exeprg = "Extract_BOM_3D.exe"

Sub CATMain()
On Error Resume Next
Shell oCATVBA_Folder.Path & "\" & exeprg, vbNormalFocus
If Err.Number <> 0 Then
MsgBox "无法调用" & exeprg & vbCrLf & "请确认" & exeprg & "存在于" & oCATVBA_Folder.Path, vbQuestion, "CATIA工具箱"
End If
End Sub

Attribute VB_Name = "Export_PDF_2D"
Option Explicit
Sub CATMain()
IntCATIA
CDF_Tool.ExportPDF oActDoc
End Sub

Attribute VB_Name = "Export_Properties_3D"
Option Explicit

Const exeprg = "Export_Properties_3D.exe"

Sub CATMain()
On Error Resume Next
Shell oCATVBA_Folder.Path & "\" & exeprg, vbNormalFocus
If Err.Number <> 0 Then
MsgBox "无法调用" & exeprg & vbCrLf & "请确认" & exeprg & "存在于" & oCATVBA_Folder.Path, vbQuestion, "CATIA工具箱"
End If
End Sub

Attribute VB_Name = "Export_Stp2_2D3D"
Option Explicit

Const exeprg = "Export_Stp2_2D3D.exe"

Sub CATMain()
On Error Resume Next
Shell oCATVBA_Folder.Path & "\" & exeprg, vbNormalFocus
If Err.Number <> 0 Then
MsgBox "无法调用" & exeprg & vbCrLf & "请确认" & exeprg & "存在于" & oCATVBA_Folder.Path, vbQuestion, "CATIA工具箱"
End If
End Sub

Attribute VB_Name = "Export_Stp_2D3D"
Option Explicit
Sub CATMain()
IntCATIA
CDF_Tool.ExportStp oActDoc
End Sub

Attribute VB_Name = "Export_Zipped_PDF_STP_2D"
Option Explicit

Const exeprg = "Export_Zipped_PDF_STP_2D.exe"

Sub CATMain()
On Error Resume Next
Shell oCATVBA_Folder.Path & "\" & exeprg, vbNormalFocus
If Err.Number <> 0 Then
MsgBox "无法调用" & exeprg & vbCrLf & "请确认" & exeprg & "存在于" & oCATVBA_Folder.Path, vbQuestion, "CATIA工具箱"
End If
End Sub

Attribute VB_Name = "FastHole_3D"
Option Explicit

Const exeprg = "FastHole.exe"

Sub CATMain()
On Error Resume Next
Shell oCATVBA_Folder.Path & "\" & exeprg, vbNormalFocus
If Err.Number <> 0 Then
MsgBox "无法调用" & exeprg & vbCrLf & "请确认" & exeprg & "存在于" & oCATVBA_Folder.Path, vbQuestion, "CATIA工具箱"
End If
End Sub

Attribute VB_Name = "Fix_Unfix_Position_3D"
Option Explicit

Const exeprg = "Fix_Unfix_Position_3D.exe"

Sub CATMain()
On Error Resume Next
Shell oCATVBA_Folder.Path & "\" & exeprg, vbNormalFocus
If Err.Number <> 0 Then
MsgBox "无法调用" & exeprg & vbCrLf & "请确认" & exeprg & "存在于" & oCATVBA_Folder.Path, vbQuestion, "CATIA工具箱"
End If
End Sub

Attribute VB_Name = "GB_Frame"
Attribute VB_Base = "0{DF3A1484-DF94-4B36-BBCC-04348D786F3E}{1B50D904-BECB-4122-B24D-FCA6D2932376}"
Attribute VB_GlobalNameSpace = False
Attribute VB_Creatable = False
Attribute VB_PredeclaredId = True
Attribute VB_Exposed = False
Attribute VB_TemplateDerived = False
Attribute VB_Customizable = False
Option Explicit
'#If VBA7 Then
'Private Declare PtrSafe Function GetPrivateProfileString Lib "kernel32" Alias "GetPrivateProfileStringA" (ByVal lpApplicationName As String, ByVal lpKeyName As Any, ByVal lpDefault As String, ByVal lpReturnedString As String, ByVal nSize As Long, ByVal lpFileName As String) As LongPtr
'Private Declare PtrSafe Function WritePrivateProfileString Lib "kernel32" Alias "WritePrivateProfileStringA" (ByVal lpApplicationName As String, ByVal lpKeyName As Any, ByVal lpString As Any, ByVal lpFileName As String) As LongPtr
'#Else
'Private Declare Function GetPrivateProfileString Lib "kernel32" Alias "GetPrivateProfileStringA" (ByVal lpApplicationName As String, ByVal lpKeyName As Any, ByVal lpDefault As String, ByVal lpReturnedString As String, ByVal nSize As Long, ByVal lpFileName As String) As Long
'Private Declare Function WritePrivateProfileString Lib "kernel32" Alias "WritePrivateProfileStringA" (ByVal lpApplicationName As String, ByVal lpKeyName As Any, ByVal lpString As Any, ByVal lpFileName As String) As Long
'#End If

Private Sub cmdNewfrmTemplate_Click()
New_From_Template.CATMain
End Sub



Private Sub cmdPjPlane_Click()
Modify_Proj_Plane_2D.CATMain
End Sub

Private Sub GB_A0_Click()

Dim sTemplate As String
sTemplate = oCATVBA_Folder("Template").Path & "\A0.CATDrawing"
InsFrame sTemplate
Unload GB_Frame
End Sub

Private Sub GB_A1_Click()

Dim sTemplate As String
sTemplate = oCATVBA_Folder("Template").Path & "\A1.CATDrawing"
InsFrame sTemplate
Unload GB_Frame

End Sub

Private Sub GB_A2_Click()

Dim sTemplate As String
sTemplate = oCATVBA_Folder("Template").Path & "\A2.CATDrawing"
InsFrame sTemplate
Unload GB_Frame

End Sub

Private Sub GB_A3_Click()

Dim sTemplate As String
sTemplate = oCATVBA_Folder("Template").Path & "\A3.CATDrawing"
InsFrame sTemplate
Unload GB_Frame

End Sub
Private Sub GB_A4_Click()

Dim sTemplate As String
sTemplate = oCATVBA_Folder("Template").Path & "\A4.CATDrawing"
InsFrame sTemplate
Unload GB_Frame

End Sub

Private Sub GB_REFRESH_Click()

RefreshTitleBlock oActDoc
Unload GB_Frame
End Sub



'************************************
'************************************


Sub InsFrame(sTemplateFile As String)

On Error Resume Next
Dim sPartName, sPartNumber, sMass, sVolume, sMaterial, sDescription, sMaterial2
sPartName = ""
sPartNumber = ""
sMass = ""
sVolume = ""
sDescription = ""

sPartName = sPartName & oActDoc.Product.Definition 'v021s修改
sPartNumber = sPartNumber & oActDoc.Product.PartNumber
sMaterial = oActDoc.Product.Nomenclature
sMaterial2 = getMaterial(oActDoc.Product)
sMass = CStr(Format(Round(oActDoc.Product.Analyze.Mass, 3), "0.000")) & "kg"
sVolume = CStr(Format(oActDoc.Product.Analyze.Volume / 1000000000, "0.000")) & "m3"
sDescription = sDescription & oActDoc.Product.DescriptionRef
Dim sDrwFileName As String
sDrwFileName = ""
sDrwFileName = oActDoc.FullName
Select Case TypeName(oActDoc)
    Case "PartDocument"
          sDrwFileName = Left(sDrwFileName, Len(sDrwFileName) - 8) & ".CATDrawing" '移除.CATPart
    Case "ProductDocument"
          sDrwFileName = Left(sDrwFileName, Len(sDrwFileName) - 11) & ".CATDrawing" '移除.CATProduct
    Case Else
End Select
If CreateObject("Scripting.FileSystemObject").FileExists(sDrwFileName) Then
   sDrwFileName = Left(sDrwFileName, Len(sDrwFileName) - 11) & "_" & CStr(Year(Now)) & CStr(Month(Now)) & CStr(Day(Now)) & ".CATDrawing"
End If

If CreateObject("Scripting.FileSystemObject").FileExists(sDrwFileName) Then
Randomize
   sDrwFileName = Left(sDrwFileName, Len(sDrwFileName) - 11) & "_" & Int(100 * Rnd) & ".CATDrawing"
End If


Set oActDoc = CATIA.Documents.NewFrom(sTemplateFile)
MsgBox "零件名称:" & vbCrLf & sPartName & vbCrLf & _
        "零件编号:" & vbCrLf & sPartNumber & vbCrLf & _
        "材料(术语):" & vbCrLf & sMaterial & vbCrLf & _
        "材料(目录树或用户属性):" & vbCrLf & sMaterial2 & vbCrLf & _
        "质量:" & vbCrLf & sMass & vbCrLf & _
        "体积:" & vbCrLf & sVolume & vbCrLf & _
        "描述:" & vbCrLf & sDescription

Dim sScale
sScale = ""
sScale = CStr(Round(oActDoc.Sheets.ActiveSheet.Scale2, 2)) & ":1"

Dim oBackGroundView, otxt, n
For n = 1 To oActDoc.Sheets.ActiveSheet.Views.Count
If oActDoc.Sheets.ActiveSheet.Views.Item(n).ViewType = 0 Then
Set oBackGroundView = oActDoc.Sheets.ActiveSheet.Views.Item(n)
End If
Next
For Each otxt In oBackGroundView.Texts
    Select Case otxt.Name
        Case "TitleName"
            otxt.Text = sPartName
        Case "TitlePN"
            otxt.Text = sPartNumber
        Case "TitleMaterial"
            otxt.Text = sMaterial
        Case "TitleMaterial2"
            otxt.Text = sMaterial2
        Case "TitleScale"
            otxt.Text = sScale
        Case "TitleMass"
            otxt.Text = sMass
        Case "TitleVolume"
            otxt.Text = sVolume
        Case "TitleDescription"
            otxt.Text = sDescription
        Case Else
    End Select
Next
On Error Resume Next
oActDoc.SaveAs sDrwFileName

End Sub
Sub RefreshTitleBlock(oDocDrw)
IntCATIA
If TypeName(CATIA.ActiveDocument) <> "DrawingDocument" Then
Exit Sub
End If
Set oActDoc = CATIA.ActiveDocument

Dim oBackGroundView, otxt, n
For n = 1 To oActDoc.Sheets.ActiveSheet.Views.Count
If oActDoc.Sheets.ActiveSheet.Views.Item(n).ViewType = 0 Then
Set oBackGroundView = oActDoc.Sheets.ActiveSheet.Views.Item(n)
End If
Next

Dim sScale
sScale = ""
sScale = CStr(Round(oActDoc.Sheets.ActiveSheet.Scale2, 2)) & ":1"

On Error Resume Next
Dim oLinkedDoc
Set oLinkedDoc = DwgLinkedDoc(oActDoc)

Dim sPartName, sPartNumber, sMass, sVolume, sMaterial, sDescription, sMaterial2
sPartName = ""
sPartNumber = ""
sMass = ""
sVolume = ""
sDescription = ""

sPartName = sPartName & oLinkedDoc.Product.Definition
sPartNumber = sPartNumber & oLinkedDoc.Product.PartNumber
sMaterial = oLinkedDoc.Product.Nomenclature  'v021s增加
sMaterial2 = getMaterial(oLinkedDoc.Product)
sMass = CStr(Format(Round(oLinkedDoc.Product.Analyze.Mass, 3), "0.000")) & "kg"
sVolume = CStr(Format(oLinkedDoc.Product.Analyze.Volume / 1000000000, "0.000")) & "m3"
sDescription = sDescription & oLinkedDoc.Product.DescriptionRef

'On Error GoTo 0

'MsgBox sPartName & vbCrLf & sPartNumber & vbCrLf & "质量:" & vbCrLf & sMass '& vbCrLf & "体积:" & sVolume
'MsgBox sPartName & vbCrLf & sPartNumber & vbCrLf & "材料:" & vbCrLf & sMaterial & vbCrLf & "质量:" & vbCrLf & sMass '& vbCrLf & "体积:" & sVolume
MsgBox "零件名称:" & vbCrLf & sPartName & vbCrLf & _
        "零件编号:" & vbCrLf & sPartNumber & vbCrLf & _
        "材料(术语):" & vbCrLf & sMaterial & vbCrLf & _
        "材料(目录树或用户属性):" & vbCrLf & sMaterial2 & vbCrLf & _
        "质量:" & vbCrLf & sMass & vbCrLf & _
        "体积:" & vbCrLf & sVolume & vbCrLf & _
        "描述:" & vbCrLf & sDescription


For Each otxt In oBackGroundView.Texts
    Select Case otxt.Name
        Case "TitleName"
            otxt.Text = sPartName
        Case "TitlePN"
            otxt.Text = sPartNumber
        Case "TitleMaterial"
            otxt.Text = sMaterial
        Case "TitleMaterial2"
            otxt.Text = sMaterial2
        Case "TitleScale"
            otxt.Text = sScale
        Case "TitleMass"
            otxt.Text = sMass
        Case "TitleVolume"
            otxt.Text = sVolume
        Case "TitleDescription"
            otxt.Text = sDescription
        Case Else
    End Select
Next

End Sub

Private Function getMaterial(oProduct1)

getMaterial = ""

'If opMat1.Value = True Then
'    getMaterial = oProduct1.Nomenclature
'Else
    Dim parameters1 ' As Parameters
    Set parameters1 = oProduct1.Parameters
    Dim i As Integer
    Dim matparacn, matparaen
    matparacn = oProduct1.PartNumber & "\" & "材料"
    matparaen = oProduct1.PartNumber & "\" & "Material"
    For i = 1 To parameters1.Count
    If (parameters1.Item(i).Name = matparacn) Or (parameters1.Item(i).Name = matparaen) Then
    getMaterial = parameters1.Item(i).ValueAsString
    End If
    Next
'End If
End Function


'Private Sub ReadConf()
'Dim sConfpath As String
'sConfpath = oCATVBA_Folder.Path
'Dim objFSO
'Set objFSO = CreateObject("Scripting.FileSystemObject")
''MsgBox sConfpath
''MsgBox Dir(sConfpath)
'If Not objFSO.FileExists(sConfpath & "\Conf1.ini") Then
'Exit Sub
'End If
''---读取配置文件---
''On Error Resume Next
'    Dim read_OK ' As Long
'    Dim read2 As String
'    read2 = String(255, 0)
'    read_OK = GetPrivateProfileString("新建图纸", "术语（Norm）用作材料", "True", read2, 256, sConfpath & "\Conf1.ini")
'    opMat1.Value = read2
'    read2 = String(255, 0)
'    read_OK = GetPrivateProfileString("新建图纸", "使用模型树中的材料名", "False", read2, 256, sConfpath & "\Conf1.ini")
'    opMat2.Value = read2
'End Sub
'Private Sub SaveConf()
'On Error Resume Next
'Dim sConfpath As String
'Dim write1 'As Long
'    '参数一： Section Name (节的名称)。
'    '参数二： 节下面的项目名称。
'    '参数三： 项目的内容。
'    '参数四： ini配置文件的路径名称。
'
'sConfpath = oCATVBA_Folder.Path
'write1 = WritePrivateProfileString("新建图纸", "术语（Norm）用作材料", CStr(opMat1.Value), sConfpath & "\Conf1.ini")
'write1 = WritePrivateProfileString("新建图纸", "使用模型树中的材料名", CStr(opMat2.Value), sConfpath & "\Conf1.ini")
'End Sub

'Private Sub UserForm_Activate()
'ReadConf
'End Sub

'Private Sub UserForm_Terminate()
'SaveConf
'End Sub


Public Sub buildPopForm(ByVal A As Object, Optional cp As String = "Properties")
'显示标题栏数据待用户确认或修改
'输入为object, 字典
If TypeName(A) <> "Dictionary" Then
Exit Sub
End If

Dim ak As Variant
ak = A.keys

Dim i, L, T
Dim crl As Object
'重设弹出的窗口尺寸
TitleBlockProperties.height = 90
TitleBlockProperties.width = 350
TitleBlockProperties.btnOK.Left = 5
TitleBlockProperties.btnOK.width = 330
TitleBlockProperties.btnOK.height = 24

For i = 0 To UBound(ak)
    Set crl = TitleBlockProperties.Frame1.Controls.Add("Forms.Label.1", ak(i), True)
    With crl
        .Caption = ak(i) & " :"
        .Left = 10
        .Top = 10 + 20 * i
        .width = TitleBlockProperties.Frame1.width / 3 - .Left - 10
        .TextAlign = 3
    End With
        TitleBlockProperties.height = TitleBlockProperties.height + 20
        TitleBlockProperties.btnOK.Top = TitleBlockProperties.height - 55

    
    Set crl = TitleBlockProperties.Frame1.Controls.Add("Forms.TextBox.1", A(ak(i))(0), True)
    With crl
        .Text = A(ak(i))(1)
        .Left = 10 + 100
        .Top = 10 + 20 * i
        .width = (TitleBlockProperties.Frame1.width / 3) * 2 - 20
    End With
Next
TitleBlockProperties.Frame1.ScrollHeight = 20 * (UBound(ak) + 2)
If TitleBlockProperties.height > 400 Then
    TitleBlockProperties.height = 400
End If
TitleBlockProperties.Frame1.height = TitleBlockProperties.height - 60
TitleBlockProperties.btnOK.Top = TitleBlockProperties.height - 55
    
TitleBlockProperties.Caption = cp
TitleBlockProperties.Show

End Sub

Public Sub AddDoc2Tree(sDocTemplate As String) 'doctype must be CATPart or CATProduct
Set oActDoc = Nothing
IntCATIA
Dim newPrdDoc As Document
Dim saveFolder As String
saveFolder = "D:"
Dim saveFullName As String

Dim doctype As String
doctype = ""
If Right(sDocTemplate, 8) = ".CATPart" Then
   doctype = ".CATPart"
ElseIf Right(sDocTemplate, 11) = ".CATProduct" Then
   doctype = ".CATProduct"
ElseIf Right(sDocTemplate, 11) = ".CATDrawing" Then
   doctype = ".CATDrawing"
End If
If doctype = "" Then
MsgBox "模板类型错误！", vbInformation, "CATIA工具箱"
Exit Sub
End If

If oActDoc Is Nothing Then
Call newDocFrom(sDocTemplate)
Exit Sub
End If

saveFolder = oActDoc.Path

Select Case TypeName(oActDoc)
    Case "ProductDocument"
        On Error Resume Next
        Set oSel = Modify_Proj_Plane_2D.Sel("Product")
        If Err.Number <> 0 Then
        Exit Sub
        Else
            
            If ProductIsComponent(oSel) Then
            saveFolder = oSel.Parent.Parent.ReferenceProduct.Parent.Path
            Else
            saveFolder = oSel.ReferenceProduct.Parent.Path
            End If
            
            If saveFolder = "" Then
            MsgBox "找不到当前所选装配的保存路径，请先保存当前再添加子件！", vbInformation + vbOKOnly, "Toolkit for CATIA"
            Exit Sub
            End If
            
            Set newPrdDoc = newDocFrom(sDocTemplate)
             If Err.Number <> 0 Then
             Exit Sub
             End If
            Err.Clear
            
            If doctype <> ".CATDrawing" Then
                saveFullName = InputBox("保存文件:", "Toolkit for CATIA", saveFolder & "\" & newPrdDoc.Product.PartNumber & doctype)
                If saveFullName <> "" Then
                    newPrdDoc.SaveAs (saveFullName)
                    If Err.Number <> 0 Then
                    MsgBox "保存时出了问题，请检查文件路径是否完整或文件是否已重名？你需要手动另存或添加！", vbInformation + vbOKOnly, "Toolkit for CATIA"
                    Exit Sub
                    End If
                Else
                    MsgBox "文件未保存,你需要手动另存或添加！", vbInformation + vbOKOnly, "Toolkit for CATIA"
                    Exit Sub
                End If
                Err.Clear
                Dim ifilelist(1)
                ifilelist(0) = newPrdDoc.FullName
                Dim DesInst As String
                DesInst = newPrdDoc.Product.Definition
                newPrdDoc.Close
                oSel.Products.AddComponentsFromFiles ifilelist, "All"
                If Err.Number <> 0 Then
                   MsgBox "无法在选定零件下添加子件！" & vbCrLf & "零件/产品已经创建，但未成功添加到当前目录树！", vbInformation + vbOKOnly, "Toolkit for CATIA"
                Else
                    If DesInst <> "" Then
                    oSel.Products.Item(oSel.Products.Count).Name = DesInst
                    End If
                End If
            Else
                saveFullName = InputBox("保存文件:", "Toolkit for CATIA", saveFolder & "\" & oSel.PartNumber & doctype)
                If saveFullName <> "" Then
                    newPrdDoc.SaveAs (saveFullName)
                    If Err.Number <> 0 Then
                    MsgBox "保存时出了问题，请检查文件路径是否完整或文件是否已重名？你需要手动另存或添加！", vbInformation + vbOKOnly, "Toolkit for CATIA"
                    Exit Sub
                    End If
                Else
                    MsgBox "文件未保存,你需要手动另存或添加！", vbInformation + vbOKOnly, "Toolkit for CATIA"
                    Exit Sub
                End If
                Err.Clear
            End If
        End If
    Case Else
         Call newDocFrom(sDocTemplate)
End Select

End Sub


Private Function newDocFrom(templatefullpath As String) As Document
On Error Resume Next
Set newDocFrom = CATIA.Documents.NewFrom(templatefullpath)
If Err.Number <> 0 Then
MsgBox "从模板新建失败，可能的原因是:" & vbCrLf & _
       "1. CATIA工具箱没有按指导安装，本插件需要安装在特定的目录下 D:\CATIA_Related\CATIA-Copilot\macros\.." & vbCrLf & _
       "2. 模板文件名包含中文或特殊字符" & vbCrLf & _
       "3. 当前使用的CATIA版本比模板文件的CATIA版本低,CATIA打不开模板文件,模板文件应当放在" & vbCrLf & _
       oCATVBA_Folder("Template\Start_Part").Path, vbInformation, "CATIA工具箱"
Exit Function
End If
If Right(templatefullpath, 11) = ".CATDrawing" Then
Exit Function
End If

'弹出窗口让用户输入必要的信息
Dim A As Variant
Set A = CreateObject("Scripting.Dictionary")
Dim oPrd
Set oPrd = newDocFrom.Product

Dim i As Integer
Dim s As String
Dim k As String
'固有属性
Dim B As Variant
B = Array("PartNumber", "Revision", "Definition", "Nomenclature", "DescriptionRef")
Randomize
For i = 0 To UBound(B)
If B(i) = "PartNumber" Then
A.Add B(i), Array(B(i), Int(100000 + (899999 * Rnd)))
Else
'a.Add b(i), Array(b(i), "")
Select Case B(i)
    Case "Revision"
    A.Add B(i), Array(B(i), oPrd.Revision)
    Case "Definition"
    A.Add B(i), Array(B(i), oPrd.Definition)
    Case "Nomenclature"
    A.Add B(i), Array(B(i), oPrd.Nomenclature)
    Case "DescriptionRef"
    A.Add B(i), Array(B(i), oPrd.DescriptionRef)
End Select
End If
Next

'固有属性

For i = 1 To oPrd.UserRefProperties.Count
    k = ""
    s = ""
    k = GetUserPropStr(oPrd.ReferenceProduct.UserRefProperties.Item(i).Name)
    s = oPrd.UserRefProperties.Item(i).ValueAsString
    'Debug.Print "k=" & k & "(" & "k" & "," & s & ")"
    A.Add k, Array(k, s)
Next

buildPopForm A, "Properties"
'从模板中新建文档

'修改新建文档的属性

End Function
Function ProductIsComponent(iProduct) As Boolean
Dim objDoc As Object
Dim objParentDoc As Object
ProductIsComponent = False
On Error Resume Next
Set objDoc = iProduct.ReferenceProduct.Parent
Set objParentDoc = iProduct.Parent.Parent.ReferenceProduct.Parent
ProductIsComponent = (objDoc Is objParentDoc)

Set objDoc = Nothing
Set objParentDoc = Nothing
Err.Clear

End Function
Function GetUserPropStr(s As String)
GetUserPropStr = Right(s, Len(s) - InStrRev(s, "\"))
End Function

Attribute VB_Name = "Gear_And_Rack_3D"
Option Explicit

Const exeprg = "Gear_And_Rack_3D.exe"

Sub CATMain()
On Error Resume Next
Shell oCATVBA_Folder.Path & "\" & exeprg, vbNormalFocus
If Err.Number <> 0 Then
MsgBox "无法调用" & exeprg & vbCrLf & "请确认" & exeprg & "存在于" & oCATVBA_Folder.Path, vbQuestion, "CATIA工具箱"
End If
End Sub

Attribute VB_Name = "Graph_ReOrder_3D"
Option Explicit

Const exeprg = "GraphTreeReOrder.exe"

Sub CATMain()
On Error Resume Next
Shell oCATVBA_Folder.Path & "\" & exeprg, vbNormalFocus
If Err.Number <> 0 Then
MsgBox "无法调用" & exeprg & vbCrLf & "请确认" & exeprg & "存在于" & oCATVBA_Folder.Path, vbQuestion, "CATIA工具箱"
End If
End Sub

Attribute VB_Name = "Hide_Datums_3D"
Option Explicit

Const exeprg = "Hide_Datums_3D.exe"

Sub CATMain()
On Error Resume Next
Shell oCATVBA_Folder.Path & "\" & exeprg, vbNormalFocus
If Err.Number <> 0 Then
MsgBox "无法调用" & exeprg & vbCrLf & "请确认" & exeprg & "存在于" & oCATVBA_Folder.Path, vbQuestion, "CATIA工具箱"
End If
End Sub

Attribute VB_Name = "Insert_GB_Frame_3D"
Option Explicit
Sub CATMain()
IntCATIA
GB_Frame.Show vbModeless
GB_Frame.Left = GB_Frame.Left * 2

End Sub

Attribute VB_Name = "MP_ReName_Export_3D"
Option Explicit

Const exeprg = "MP_ReName_Export_3D.exe"

Sub CATMain()
On Error Resume Next
Shell oCATVBA_Folder.Path & "\" & exeprg, vbNormalFocus
If Err.Number <> 0 Then
MsgBox "无法调用" & exeprg & vbCrLf & "请确认" & exeprg & "存在于" & oCATVBA_Folder.Path, vbQuestion, "CATIA工具箱"
End If
End Sub

Attribute VB_Name = "Modify_Proj_Plane_2D"
Option Explicit
Sub CATMain()
On Error Resume Next
IntCATIA
'MsgBox CATIA.Windows.Item(1).Caption
Select Case TypeName(oActDoc)
    Case "DrawingDocument"
    Case Else
        MsgBox "只能在工程制图工作台操作这个命令"
    Exit Sub
End Select

Dim V5Lang As String
V5Lang = GetV5Lang
Debug.Print "V5界面语言是 " & V5Lang
Dim oMyWindow As Object
Dim o3DWindow As Object
Dim sMyCaption As String
Dim s3DCaption As String
Dim FlagFind As Boolean
FlagFind = False
sMyCaption = CATIA.ActiveWindow.Caption
Dim oMyView As Object
Err.Clear
           On Error Resume Next
                Set oMyView = Sel("DrawingView")
                If Err.Number <> 0 Then
                Exit Sub
                End If
                   Select Case oMyView.ViewType
                            Case catViewFront
                            Case Else
                            MsgBox "只能选择主视图", vbInformation
                            Exit Sub
                   End Select
oMyView.Activate
'MsgBox TypeName(oMyView.GenerativeBehavior.Document.Parent)
Select Case TypeName(oMyView.GenerativeBehavior.Document.Parent) '多实体模式是Bodies
    Case "Bodies"
        s3DCaption = oMyView.GenerativeBehavior.Document.Parent.Parent.Parent.Name  '如果是多实体模式需要多两个Parent
        '查询数模窗口是否打开
        Set oMyWindow = CATIA.ActiveWindow
        For Each o3DWindow In CATIA.Windows
        If o3DWindow.Caption = s3DCaption Then
        FlagFind = True
        Exit For
        End If
        Next
        
        If FlagFind = False Then
        CATIA.Documents.Open oMyView.GenerativeBehavior.Document.Parent.Parent.Parent.FullName
        Set o3DWindow = CATIA.ActiveWindow
        FlagFind = True
        End If
        oMyWindow.Activate
        oMyView.Activate
        Set oSel = oActDoc.Selection
        oSel.Clear
        oSel.Add oMyView
    Case Else
        s3DCaption = oMyView.GenerativeBehavior.Document.Parent.Name
        '查询数模窗口是否打开
        Set oMyWindow = CATIA.ActiveWindow
        For Each o3DWindow In CATIA.Windows
        If o3DWindow.Caption = s3DCaption Then
        FlagFind = True
        Exit For
        End If
        Next
        
        If FlagFind = False Then
        CATIA.Documents.Open oMyView.GenerativeBehavior.Document.Parent.FullName
        Set o3DWindow = CATIA.ActiveWindow
        FlagFind = True
        End If
        oMyWindow.Activate
        oMyView.Activate
        Set oSel = oActDoc.Selection
        oSel.Clear
        oSel.Add oMyView
End Select


If V5Lang = "English" Then
CATIA.StartCommand "Modify Projection Plane"
Debug.Print "执行 Modify Projection Plane"
ElseIf V5Lang = "Simplified Chinese" Then
CATIA.StartCommand "修改投影平面"
Debug.Print "执行 修改投影平面"
End If
o3DWindow.Activate
End Sub
Function GetV5Lang() As String
Dim s As Object
Set s = CATIA.ActiveDocument.Selection
s.Clear
Dim stu As String
stu = CATIA.StatusBar
stu = LTrim(stu)
stu = Mid(stu, 1, 1) '第一个字符
Select Case Asc(UCase(stu))
Case 65 To 90           'A-Z
GetV5Lang = "English"
Case Else
GetV5Lang = "Simplified Chinese"
End Select
End Function
Function Sel(ObjType As String, Optional ObjType2 As String, Optional ObjType3 As String)
Dim S2, InputObjectType(), Status, NotSel, obj, Picked
Set S2 = CATIA.ActiveDocument.Selection
S2.Clear

If ObjType2 = "" Then
        ReDim InputObjectType(0)
        InputObjectType(0) = ObjType
        ElseIf ObjType3 = "" Then
                ReDim InputObjectType(1)
                InputObjectType(0) = ObjType
                InputObjectType(1) = ObjType2
                Else
                    ReDim InputObjectType(2)
                    InputObjectType(0) = ObjType
                    InputObjectType(1) = ObjType2
                    InputObjectType(2) = ObjType3
End If

Dim indication, n
indication = ""
For n = 0 To UBound(InputObjectType)
    indication = indication & "," & InputObjectType(n)
Next

Picked = False
NotSel = True
    Do While NotSel
        Status = S2.SelectElement2(InputObjectType, "Select the " & indication, False)
        If (Status = "Cancel") Then
            Set Sel = Nothing 'modified 20200616
            MsgBox "已退出选择", vbSystemModal
            Exit Function
        ElseIf (Status = "Redo" And Not Picked) Then
               ElseIf (Status = "Undo") Then
                        Exit Function
                    ElseIf (Status <> "Redo") Then Set obj = S2.Item(1).Value
                              Picked = True
                              NotSel = False
        End If
    Loop
    S2.Clear
    Set Sel = obj
End Function

Attribute VB_Name = "New_From_Template"
Option Explicit
Sub CATMain()

IntCATIA

NewfrmTemplate.Show vbModeless
NewfrmTemplate.Left = NewfrmTemplate.Left * 2
End Sub

Attribute VB_Name = "NewfrmTemplate"
Attribute VB_Base = "0{C3A34416-8F4B-4303-B937-9738A52D8938}{D5266603-38A9-47C9-8000-8493EFE033D4}"
Attribute VB_GlobalNameSpace = False
Attribute VB_Creatable = False
Attribute VB_PredeclaredId = True
Attribute VB_Exposed = False
Attribute VB_TemplateDerived = False
Attribute VB_Customizable = False
Option Explicit

Private Sub lstTemplate_DblClick(ByVal Cancel As MSForms.ReturnBoolean)
Dim sTempfile As String
Dim i As Integer
sTempfile = ""
For i = 0 To lstTemplate.ListCount - 1
    If lstTemplate.Selected(i) = True Then
        sTempfile = lstTemplate.List(i)
        Exit For
    End If
Next

If sTempfile <> "" Then
GB_Frame.AddDoc2Tree oCATVBA_Folder("Template\Start_Part").Path & "\" & sTempfile
End If
End Sub

Private Sub UserForm_Initialize()
'1.扫描所有..\Template\Start_Part文件夹下的CATPart,CATDrawing和CATProduct文件，并将文件名放入数组
'2.数组内容添加执行按钮
Dim f, fso, fname
    Set fso = CreateObject("Scripting.FileSystemObject")
    For Each f In oCATVBA_Folder("Template\Start_Part").Files
        fname = f.Name
        If Right(f.Name, 8) = ".CATPart" Then
           lstTemplate.AddItem f.Name
        ElseIf Right(f.Name, 11) = ".CATProduct" Then
           lstTemplate.AddItem f.Name
        ElseIf Right(f.Name, 11) = ".CATDrawing" Then
           lstTemplate.AddItem f.Name
        End If
    Next
End Sub

Attribute VB_Name = "Open_Current_Folder"
#If VBA7 Then
Private Declare PtrSafe Function FindWindow Lib "user32" Alias "FindWindowA" (ByVal lpClassName As String, ByVal lpWindowName As String) As LongPtr
Private Declare PtrSafe Function ShowWindow Lib "user32" (ByVal hwnd As LongPtr, ByVal nCmdShow As LongPtr) As LongPtr
Private Declare PtrSafe Function SetWindowPos Lib "user32" (ByVal hwnd As LongPtr, ByVal hWndInsertAfter As LongPtr, ByVal x As LongPtr, ByVal y As LongPtr, ByVal cx As LongPtr, ByVal cy As LongPtr, ByVal wFlags As LongPtr) As LongPtr
#Else
Private Declare Function FindWindow Lib "user32" Alias "FindWindowA" (ByVal lpClassName As String, ByVal lpWindowName As String) As Long
Private Declare Function ShowWindow Lib "user32" (ByVal hwnd As Long, ByVal nCmdShow As Long) As Long
Private Declare Function SetWindowPos Lib "user32" (ByVal hwnd As Long, ByVal hWndInsertAfter As Long, ByVal x As Long, ByVal y As Long, ByVal cx As Long, ByVal cy As Long, ByVal wFlags As Long) As Long
Dim winHwnd As Long
#End If

Sub CATMain()
IntCATIA
Err.Clear

On Error Resume Next
Dim s As String
s = oActDoc.Path
If Err.Number <> 0 Then
Exit Sub
End If
If CreateObject("Scripting.FileSystemObject").FolderExists(s) = False Then
MsgBox "文件夹不存在,当前活动文档是否并未保存？", vbInformation, "CATIA工具箱"
Exit Sub
End If
winHwnd = FindWindow(vbNullString, Right(s, Len(s) - InStrRev(s, "\")))
'MsgBox winHwnd
If winHwnd <> 0 Then
ShowWindow winHwnd, 9
SetWindowPos winHwnd, 0, 100, 100, 800, 600, &H40
'ShowWindow winHwnd, 5
Else
    Shell "explorer.exe " & s, vbNormalFocus
End If

End Sub

Attribute VB_Name = "Open_Drawing_Model_3D"
Option Explicit
Sub CATMain()
IntCATIA
On Error Resume Next
If oActDoc Is Nothing Then
Exit Sub
End If
If TypeName(oActDoc) <> "ProductDocument" And TypeName(oActDoc) <> "PartDocument" And TypeName(oActDoc) <> "DrawingDocument" Then
MsgBox "当前活动文档不是.CATProduct或.CATPart或.CATDrawing!"
Exit Sub
End If

Dim shortName As String
Debug.Print TypeName(oActDoc)
Select Case TypeName(oActDoc)
Case "ProductDocument"
     shortName = Replace(oActDoc.Name, ".CATProduct", "")
Case "PartDocument"
     shortName = Replace(oActDoc.Name, ".CATPart", "")
Case "DrawingDocument"
     CATIA.Documents.Open DwgLinkedDoc(oActDoc).FullName
     Exit Sub
Case Else
End Select

Dim fso1, file1, n1
n1 = 0
Dim arr() As String
Set fso1 = CreateObject("Scripting.FileSystemObject")
For Each file1 In fso1.GetFolder(oActDoc.Path).Files
    If (InStr(file1.Name, ".CATDrawing") > 0) And (InStr(file1.Name, shortName) > 0) Then
    ReDim Preserve arr(n1)
    arr(n1) = oActDoc.Path & "\" & file1.Name
    n1 = n1 + 1
    End If
Next
If n1 = 1 Then
CATIA.Documents.Open arr(n1 - 1)
ElseIf n1 > 1 Then
    Dim i As Integer
    Dim drwlist As String
    Dim shortDrwName As String
    For i = 0 To n1 - 1
    shortDrwName = Right(arr(i), Len(arr(i)) - InStrRev(arr(i), "\"))
    drwlist = drwlist & vbCrLf & shortDrwName
    Next
    If (MsgBox("当前文件夹下找到疑似工程图" & UBound(arr) + 1 & "个，需要手动打开工程图吗？" & vbCrLf & drwlist, vbQuestion + vbYesNo, "CATIA工具箱") = vbYes) Then
    Open_Current_Folder.CATMain
    End If
ElseIf n1 < 1 Then
    If (MsgBox("当前文件夹下找不到对应工程图！需要手动打开文件夹吗？", vbQuestion + vbYesNo, "CATIA工具箱") = vbYes) Then
    Open_Current_Folder.CATMain
    End If
End If
Set fso1 = Nothing
Set file1 = Nothing
End Sub

Attribute VB_Name = "PartBodiesReOrder_3D"
Option Explicit

Const exeprg = "PartBodiesReOrder.exe"

Sub CATMain()
On Error Resume Next
Shell oCATVBA_Folder.Path & "\" & exeprg, vbNormalFocus
If Err.Number <> 0 Then
MsgBox "无法调用" & exeprg & vbCrLf & "请确认" & exeprg & "存在于" & oCATVBA_Folder.Path, vbQuestion, "CATIA工具箱"
End If
End Sub

Attribute VB_Name = "Part_2_Product_3D"
Option Explicit

Const exeprg = "Part_2_Product_3D.exe"

Sub CATMain()
On Error Resume Next
Shell oCATVBA_Folder.Path & "\" & exeprg, vbNormalFocus
If Err.Number <> 0 Then
MsgBox "无法调用" & exeprg & vbCrLf & "请确认" & exeprg & "存在于" & oCATVBA_Folder.Path, vbQuestion, "CATIA工具箱"
End If
End Sub

Attribute VB_Name = "Random_Color_3D"
Option Explicit

Const exeprg = "Random_Color_3D.exe"

Sub CATMain()
On Error Resume Next
Shell oCATVBA_Folder.Path & "\" & exeprg, vbNormalFocus
If Err.Number <> 0 Then
MsgBox "无法调用" & exeprg & vbCrLf & "请确认" & exeprg & "存在于" & oCATVBA_Folder.Path, vbQuestion, "CATIA工具箱"
End If
End Sub

Attribute VB_Name = "Select_Dims_2D"
Option Explicit
Sub CATMain()
IntCATIA
SelectDims oActDoc
End Sub

Sub SelectDims(oDocDrw)
On Error Resume Next
If TypeName(oDocDrw) <> "DrawingDocument" Then
MsgBox "此命令只能在工程制图模块下运行!"
Exit Sub
End If
    Dim Selection
    Dim Status
    Dim InputObjectType(0)
    InputObjectType(0) = "DrawingDimension"
        
    Set Selection = oDocDrw.Selection
    Selection.Clear
    Do Until (Status = "Cancel" Or Status = "Undo" Or Status = "Redo")
    Status = Selection.SelectElement3(InputObjectType, "Please select dimensions", False, CATMultiSelTriggWhenUserValidatesSelection, False)
    If Status = "Normal" Then Exit Do
    Loop
End Sub
'Func SelectElement3( CATSafeArrayVariant  iFilterType, CATBSTR  iMessage, boolean  iObjectSelectionBeforeCommandUsePossibility, CATMultiSelectionMode  iMultiSelectionMode, boolean  iTooltip) As CATBSTR

Attribute VB_Name = "Send_2_SubFolder_3D"
Option Explicit

Const exeprg = "SendToSubFolders.exe"
Sub CATMain()
On Error Resume Next
Shell oCATVBA_Folder.Path & "\" & exeprg, vbNormalFocus
If Err.Number <> 0 Then
MsgBox "无法调用" & exeprg & vbCrLf & "请确认" & exeprg & "存在于" & oCATVBA_Folder.Path, vbQuestion, "CATIA工具箱"
End If
End Sub

Attribute VB_Name = "Table_2_Excel_2D"
Option Explicit
Sub CATMain()
IntCATIA
Table2Excel oActDoc
End Sub

Sub Table2Excel(oDocDrw)
If TypeName(oDocDrw) <> "DrawingDocument" Then
MsgBox "此命令只能在工程制图模块下运行!"
Exit Sub
End If

Dim drwtable As DrawingTable
Dim objWorkbook
Dim objSheet
Dim objCell
Dim InputObjectType(0)
Dim R, C
Dim IsExcelRunning As Boolean

Dim DrwSheets
Set DrwSheets = oDocDrw.Sheets


    Dim Selection
    Dim WindowLocation(1)
    Dim Status, xCenter, YCenter 'InputObjectType(0)
    Dim ObjectSelected

    Status = "MouseMove"
    InputObjectType(0) = "DrawingTable"
    ObjectSelected = False
        
    Set Selection = oDocDrw.Selection
    Selection.Clear
    
    Do While ObjectSelected = False
        Status = Selection.IndicateOrSelectElement2D("Please select drawing table to export", InputObjectType, True, True, True, ObjectSelected, WindowLocation)

    If (Status = "Cancel" Or Status = "Undo" Or Status = "Redo") Then
        MsgBox "你没有选择表格，程序退出!"
        Exit Sub
    End If
       
    Loop
    
    If ObjectSelected Then
       Set drwtable = Selection.Item(1).Value
    End If
    
Dim totalrows, totalcolumns
totalrows = drwtable.NumberOfRows
totalcolumns = drwtable.NumberOfColumns
Dim table()
ReDim table(totalrows, totalcolumns)
For R = 1 To totalrows
For C = 1 To totalcolumns
table(R, C) = drwtable.GetCellString(R, C)
Next
Next

IntExcel

objExcel.Visible = True

Dim myname
myname = Replace(oDocDrw.FullName & "_" & drwtable.Name, ".", "_") & ".xlsx"
Set objWorkbook = objExcel.workbooks.Add()
objWorkbook.Activate
Set objSheet = objWorkbook.Worksheets.Item(1)
'--Populate spreadsheet with values from array.
For R = 1 To totalrows
For C = 1 To totalcolumns
objSheet.cells(R, C) = table(R, C)
Next
Next
On Error Resume Next
objWorkbook.SaveAs myname
If Err.Number <> 0 Then
  MsgBox "没有权限保存文件" & vbNewLine & vbNewLine & myname & vbNewLine & vbNewLine & "请关闭已打开的文件或使用其他文件名手动另存", vbInformation, "Save excel failure"
End If
On Error GoTo 0
'objWorkbook.Close
'objExcel.Quit ' Close Excel with the Quit method on the Application object
'MsgBox "Your Catia drawing table has been exported to Excel." & vbNewLine & vbNewLine & myname, vbInformation, "Table Export Complete"
End Sub

Attribute VB_Name = "TextOnPlanarFace"
Attribute VB_Base = "0{C7473FCD-8096-4A01-8A09-6A57C6E98286}{600D9A8E-320F-43D4-9900-E36762DC7809}"
Attribute VB_GlobalNameSpace = False
Attribute VB_Creatable = False
Attribute VB_PredeclaredId = True
Attribute VB_Exposed = False
Attribute VB_TemplateDerived = False
Attribute VB_Customizable = False
Option Explicit
#If VBA7 Then
Private Declare PtrSafe Function ShellExecute Lib "shell32.dll" Alias "ShellExecuteA" (ByVal hwnd As LongPtr, ByVal lpOperation As String, ByVal lpFile As String, ByVal lpParameters As String, ByVal lpDirectory As String, ByVal nShowCmd As Long) As LongPtr
Private Declare PtrSafe Function GetPrivateProfileString Lib "kernel32" Alias "GetPrivateProfileStringA" (ByVal lpApplicationName As String, ByVal lpKeyName As Any, ByVal lpDefault As String, ByVal lpReturnedString As String, ByVal nSize As LongPtr, ByVal lpFileName As String) As LongPtr
Private Declare PtrSafe Function WritePrivateProfileString Lib "kernel32" Alias "WritePrivateProfileStringA" (ByVal lpApplicationName As String, ByVal lpKeyName As Any, ByVal lpString As Any, ByVal lpFileName As String) As LongPtr
#Else
Private Declare Function ShellExecute Lib "shell32.dll" Alias "ShellExecuteA" (ByVal hwnd As Long, ByVal lpOperation As String, ByVal lpFile As String, ByVal lpParameters As String, ByVal lpDirectory As String, ByVal nShowCmd As Long) As Long
Private Declare Function GetPrivateProfileString Lib "kernel32" Alias "GetPrivateProfileStringA" (ByVal lpApplicationName As String, ByVal lpKeyName As Any, ByVal lpDefault As String, ByVal lpReturnedString As String, ByVal nSize As Long, ByVal lpFileName As String) As Long
Private Declare Function WritePrivateProfileString Lib "kernel32" Alias "WritePrivateProfileStringA" (ByVal lpApplicationName As String, ByVal lpKeyName As Any, ByVal lpString As Any, ByVal lpFileName As String) As Long
#End If
Const cmdCaption = "开始刻字"
Const cmdBackColor = &H8000000F
Const cmdBackColorRuning = &HFFFF&
Private m_colHandlers As Collection
Dim selPlanarFace, selEdge As Object
Dim tarBody As Body: Dim tarHybridBody As HybridBody: Dim tarPart As Part
Dim sketchVariantOfDouble(8) '草图方向，也是计算的新坐标系
Dim CoGCoordInUserAxis(1) As Double '所选平面重心点C在用户坐标系中的坐标，可正可负
Dim xCenter As Double '所选X线段的半，用于X居中Y输入的情况，永远为正
Dim extrueSketch As Boolean
Dim text2write As String

'####################执行按钮##########################
Private Sub cmdRun_Click()
If CATIA.ActiveDocument Is Nothing Then Exit Sub
Set oActDoc = CATIA.ActiveDocument
If TypeName(oActDoc) <> "PartDocument" Then
    MsgBox "此命令只能在零件设计模块下运行", , "CATIA工具箱|平面刻字"
    Exit Sub
End If

If txtInput.Text = "" Then
    MsgBox "要刻字的内容为空！请输入要刻字的内容再运行！"
    Exit Sub
End If

Set selPlanarFace = Nothing: Set selEdge = Nothing
Set tarBody = Nothing: Set tarPart = Nothing
CoGCoordInUserAxis(0) = 0: CoGCoordInUserAxis(1) = 0
text2write = ""
If Val(cbxHeight.Text) = 0 Then
extrueSketch = False
Else
extrueSketch = True
End If

Dim A(2) As Double, B(2) As Double, C(2) As Double, z(2) As Double, yUp(2) As Double
Dim Origin(2) As Double, XAxis(2) As Double, YAxis(2) As Double, ZAxis(2) As Double

cmdRun.Caption = "请选择刻字平面"
cmdRun.BackColor = cmdBackColorRuning
Set selPlanarFace = Sel("PlanarFace")
If selPlanarFace Is Nothing Then
    cmdRun.Caption = cmdCaption
    cmdRun.BackColor = cmdBackColor
    Exit Sub
End If
cmdRun.Caption = "请选择平面内的线段作为X轴"
Set selEdge = Sel("RectilinearTriDimFeatEdge", "RectilinearBiDimFeatEdge", "RectilinearMonoDimFeatEdge")
If selEdge Is Nothing Then
    cmdRun.Caption = cmdCaption
    cmdRun.BackColor = cmdBackColor
    Exit Sub
End If

'取得平面所属于的Body或几何图形集以及Part
Dim nodeType
Set nodeType = selPlanarFace
Do While (TypeName(nodeType) <> "PartDocument")
    Set nodeType = nodeType.Parent
    If TypeName(nodeType) = "Body" Then
    Set tarBody = nodeType
    End If
    If TypeName(nodeType) = "HybridBody" Then
    Set tarHybridBody = nodeType
    End If
    If TypeName(nodeType) = "Part" Then
    Set tarPart = nodeType
    End If
Loop
If tarBody Is Nothing Then
   If MsgBox("所选平面不属于任何实体！只能创建草图不能创建凸凹字，需要继续吗?", vbQuestion + vbYesNo) = vbNo Then
        cmdRun.Caption = cmdCaption
        cmdRun.BackColor = cmdBackColor
        Exit Sub
   End If
   extrueSketch = False
   tarPart.InWorkObject = tarHybridBody
Else
   tarPart.InWorkObject = tarBody
End If

'取得平面法向向量，可能向内也可能向外
Dim tX(2): Dim tY(2)
selPlanarFace.GetFirstAxis tX
selPlanarFace.GetSecondAxis tY
Dim tX1(2) As Double: Dim tY1(2) As Double: Dim tZ(2) As Double
tX1(0) = tX(0): tX1(1) = tX(1): tX1(2) = tX(2)
tY1(0) = tY(0): tY1(1) = tY(1): tY1(2) = tY(2)
CrossProduct tX1, tY1, tZ
NormalizeVector tZ
'取得平面质心作为点C
Dim objSPAWkb
Set objSPAWkb = CATIA.ActiveDocument.GetWorkbench("SPAWorkbench")
Dim objRef As Object
Dim objMeasurable
'Set objRef = oActDoc.Part.CreateReferenceFromObject(selPlanarFace)
Set objMeasurable = objSPAWkb.GetMeasurable(selPlanarFace)
Dim C0(2)
objMeasurable.GetCOG C0
C(0) = C0(0): C(1) = C0(1): C(2) = C0(2)
'Debug.Print "平面重心C: (" & C(0) & ", " & C(1) & ", " & C(2) & ")"

'从屏幕由内往外方向作为用户坐标系Z轴参考，屏幕向上方向作为用户坐标系Y轴参考
Dim ActViewer As Viewer3D
Dim varViewer As Variant
Set ActViewer = CATIA.ActiveWindow.ActiveViewer
Set varViewer = ActViewer
' get viewpoint
Dim varViewpoint As Variant
Dim ActViewpoint As Viewpoint3D
Set ActViewpoint = ActViewer.Viewpoint3D
Set varViewpoint = ActViewpoint
Dim vDirectionSight(2) As Variant
varViewpoint.GetSightDirection vDirectionSight
z(0) = vDirectionSight(0) * (-1): z(1) = vDirectionSight(1) * (-1): z(2) = vDirectionSight(2) * (-1)

'Debug.Print "从屏幕由内往外方向: (" & Z(0) & ", " & Z(1) & ", " & Z(2) & ")"
Dim vDirectionUp(2) As Variant
varViewpoint.GetUpDirection vDirectionUp
yUp(0) = vDirectionUp(0): yUp(1) = vDirectionUp(1): yUp(2) = vDirectionUp(2)

Dim pointOnCurve(8)
Set objRef = Nothing: Set objMeasurable = Nothing
Set objMeasurable = objSPAWkb.GetMeasurable(selEdge)
objMeasurable.GetPointsOnCurve pointOnCurve
A(0) = pointOnCurve(0): A(1) = pointOnCurve(1): A(2) = pointOnCurve(2)
B(0) = pointOnCurve(6): B(1) = pointOnCurve(7): B(2) = pointOnCurve(8)

xCenter = objMeasurable.length / 2

' 计算用户坐标系
On Error GoTo ErrorHandler
CalculateUserCoordinateSystem A, B, C, z, yUp, CoGCoordInUserAxis, Origin, XAxis, YAxis, ZAxis
If AreUnitVectorsParallel(tZ, ZAxis) = False Then
    MsgBox "所选直线边不属于所选平面！刻字终止！", vbExclamation + vbOKOnly
    cmdRun.Caption = cmdCaption
    cmdRun.BackColor = cmdBackColor
    Exit Sub
End If

sketchVariantOfDouble(0) = Origin(0): sketchVariantOfDouble(1) = Origin(1): sketchVariantOfDouble(2) = Origin(2)
sketchVariantOfDouble(3) = XAxis(0): sketchVariantOfDouble(4) = XAxis(1): sketchVariantOfDouble(5) = XAxis(2)
sketchVariantOfDouble(6) = YAxis(0): sketchVariantOfDouble(7) = YAxis(1): sketchVariantOfDouble(8) = YAxis(2)

'刻字内容
Select Case cbxInputType.ListIndex
    Case 0
        text2write = txtInput.Text
    Case 1
        text2write = tarPart.Parent.Product.PartNumber
    Case 2
        If tarBody Is Nothing Then
        text2write = tarHybridBody.Name
        Else
        text2write = tarBody.Name
        End If
    Case Else
        text2write = txtInput.Text
End Select
    
CreateText text2write
cmdRun.Caption = cmdCaption
cmdRun.BackColor = cmdBackColor
Exit Sub
ErrorHandler:
    MsgBox "错误: " & Err.Description, vbExclamation
    cmdRun.Caption = cmdCaption
    cmdRun.BackColor = cmdBackColor
End Sub

'##############布局更改时显示或隐藏XY##################
Private Sub cbxLocation_Click()
Select Case cbxLocation.ListIndex
    Case 0
        cbxX.Enabled = False: cbxY.Enabled = False
        cbxX.Visible = False: cbxY.Visible = False
        txtInput.TextAlign = fmTextAlignCenter
    Case 1
        cbxX.Enabled = False: cbxY.Enabled = True
        cbxX.Visible = False: cbxY.Visible = True
        txtInput.TextAlign = fmTextAlignCenter
    Case 2
        cbxX.Enabled = True: cbxY.Enabled = True
        cbxX.Visible = True: cbxY.Visible = True
        txtInput.TextAlign = fmTextAlignLeft
End Select
End Sub

'####################切换字体##########################
Private Sub cbxFontName_Click()
If IsStrokeFont(cbxFontName.Text) Then
    '单线字体：显示加厚选项，无法预览字形
    cbxThickness.Enabled = True: cbxThickness.Visible = True
Else
    '轮廓字体（TrueType等）：隐藏加厚选项，可预览字形
    cbxThickness.Enabled = False: cbxThickness.Visible = False
    On Error Resume Next
    SetPreviewFont txtInput, cbxFontName.Text
    SetPreviewFont txtSpecial, cbxFontName.Text
    On Error GoTo 0
End If
End Sub
'####################切换输入类型##########################
Private Sub cbxInputType_Click()
If cbxInputType.ListIndex = 0 Then
txtInput.Enabled = True: txtInput.Text = ""
Else
txtInput.Text = "--自动提取，无需输入--": txtInput.Enabled = False
End If
End Sub
'####################切换字高##########################
Private Sub cbxFontSize_Click()
txtInput.Font.Size = Val(cbxFontSize.Text) * 2.8346 + 4
End Sub
'####################选择字高##########################
Private Sub cbxFontSize_LostFocus()
txtInput.Font.Size = Val(cbxFontSize.Text) * 2.8346 + 4
End Sub

'####################选择对象##########################
Public Function Sel(ObjType As String, Optional ObjType2 As String, Optional ObjType3 As String)
Dim S2, InputObjectType(), Status, NotSel, obj, Picked
Set S2 = CATIA.ActiveDocument.Selection
S2.Clear

If ObjType2 = "" Then
        ReDim InputObjectType(0)
        InputObjectType(0) = ObjType
        ElseIf ObjType3 = "" Then
                ReDim InputObjectType(1)
                InputObjectType(0) = ObjType
                InputObjectType(1) = ObjType2
                Else
                    ReDim InputObjectType(2)
                    InputObjectType(0) = ObjType
                    InputObjectType(1) = ObjType2
                    InputObjectType(2) = ObjType3
End If

Dim indication, n
indication = ""
For n = 0 To UBound(InputObjectType)
    indication = indication & "," & InputObjectType(n)
Next

Picked = False
NotSel = True
    Do While NotSel
        Status = S2.SelectElement2(InputObjectType, "Select the " & indication, False)
        If (Status = "Cancel") Then
            Set Sel = Nothing 'modified 20200616
            MsgBox "已退出选择", vbSystemModal
            Exit Function
        ElseIf (Status = "Redo" And Not Picked) Then
               ElseIf (Status = "Undo") Then
                        Exit Function
                    ElseIf (Status <> "Redo") Then Set obj = S2.Item2(1).Value
                              Picked = True
                              NotSel = False
        End If
    Loop
    S2.Clear
    Set Sel = obj
End Function

'##############创建字符####################################
Private Sub CreateText(txt0 As String)
If txt0 = "" Then
MsgBox "要刻字的内容为空！请输入要刻字的内容再运行！"
Exit Sub
End If

Dim NowWin
Set NowWin = CATIA.ActiveWindow
Dim settingRepository1
On Error Resume Next
Set settingRepository1 = CATIA.SettingControllers.Item("DXF")
settingRepository1.Commit '暂存当前设置
settingRepository1.PutAttr "ImportUnit", 0 'Millimeter
settingRepository1.PutAttr "ExportMode", 1 'Graphic
On Error GoTo 0
Dim TemDoc As DrawingDocument: Dim TemText As DrawingText: Dim TemTextDXF As String
TemTextDXF = oCATVBA_Folder("Temp") & "\" & Right$("0" & CStr(Minute(Now)), 2) & Right$("0" & CStr(Second(Now)), 2) & ".dxf"
Set TemDoc = CATIA.Documents.Add("Drawing")
TemDoc.Standard = catISO
Set TemText = TemDoc.Sheets.ActiveSheet.Views.ActiveView.Texts.Add(txt0, 0, 0)
TemDoc.Sheets.ActiveSheet.ForceUpdate
TemText.SetFontName 0, 0, cbxFontName.Text
TemText.SetFontSize 0, 0, CDbl(cbxFontSize.Text)
TemText.SetParameterOnSubString 15, 0, 0, Val(cbxSpacing.Text) * 100
Select Case cbxLocation.ListIndex
Case 0
TemText.AnchorPosition = 5 'catMiddleCenter
TemText.x = CoGCoordInUserAxis(0): TemText.y = CoGCoordInUserAxis(1)
Case 1
TemText.AnchorPosition = 6 'catBottomCenter
TemText.x = xCenter: TemText.y = Val(cbxY.Text)
Case 2
TemText.AnchorPosition = 3 'catBottomLeft
TemText.x = Val(cbxX.Text): TemText.y = Val(cbxY.Text)
Case Else
TemText.AnchorPosition = 3 'catBottomLeft
TemText.x = 0: TemText.y = 0
End Select
TemDoc.Sheets.ActiveSheet.ForceUpdate
Select Case cbxMirror.ListIndex
Case 0
TemText.TextProperties.Mirror = 0 ' catTextNoFlip
Case 1
TemText.TextProperties.Mirror = 1 ' catTextHorizontalFlip
Case 2
TemText.TextProperties.Mirror = 2 ' catTextVerticalFlip
Case 3
TemText.TextProperties.Mirror = 3 ' catTextHorizontalAndVerticalFlip
End Select
TemDoc.Sheets.ActiveSheet.ForceUpdate
TemDoc.Update
TemDoc.ExportData TemTextDXF, "dxf"
TemDoc.Update
TemDoc.Close
Dim TemDoc2
Set TemDoc2 = CATIA.Documents.Open(TemTextDXF)
Dim TemSlct
Set TemSlct = CATIA.ActiveDocument.Selection
TemSlct.Clear
Dim colGeometry As GeometricElements
Set colGeometry = CATIA.ActiveDocument.Sheets.ActiveSheet.Views.ActiveView.GeometricElements
Dim tempPolyline
For Each tempPolyline In colGeometry
TemSlct.Add tempPolyline
Next
TemSlct.Copy
NowWin.Activate
Dim sketch1, sketch1Variant
If tarBody Is Nothing Then
Set sketch1 = tarHybridBody.HybridSketches.Add(selPlanarFace)
Else
Set sketch1 = tarBody.Sketches.Add(selPlanarFace)
End If
Set sketch1Variant = sketch1
sketch1Variant.SetAbsoluteAxisData sketchVariantOfDouble
sketch1.OpenEdition
CATIA.ActiveDocument.Selection.Clear
CATIA.ActiveDocument.Selection.Add sketch1
CATIA.ActiveDocument.Selection.Paste
CATIA.ActiveDocument.Selection.Clear
sketch1.CloseEdition
sketch1.Name = "TextSketch_" & Right$("0" & CStr(Minute(Now)), 2) & Right$("0" & CStr(Second(Now)), 2)
tarPart.Update
TemDoc2.Close
On Error Resume Next
settingRepository1.Rollback '恢复设置
On Error GoTo 0
Kill TemTextDXF
If extrueSketch = False Then
tarPart.Update
Exit Sub
End If

Dim Tempad
On Error Resume Next
Err.Clear
If Not IsStrokeFont(cbxFontName.Text) Then '不是单线字体
    If Val(cbxHeight.Text) > 0 Then
    Set Tempad = tarPart.ShapeFactory.AddNewPad(sketch1, Val(cbxHeight.Text))
    Tempad.SecondLimit.LimitMode = 3 'catUpToPlaneLimit
    Tempad.SecondLimit.LimitingElement = selPlanarFace
    Tempad.Name = "TextPad"
    Else
    Set Tempad = tarPart.ShapeFactory.AddNewPocket(sketch1, Abs(Val(cbxHeight.Text)))
    Tempad.SecondLimit.LimitMode = 3 'catUpToPlaneLimit
    Tempad.SecondLimit.LimitingElement = selPlanarFace
    Tempad.Name = "TextPocket"
    End If
End If
If IsStrokeFont(cbxFontName.Text) And Val(cbxThickness.Text) > 0 Then '单线字体且加厚值不等于0
    If Val(cbxHeight.Text) > 0 Then
    Set Tempad = tarPart.ShapeFactory.AddNewPad(sketch1, Val(cbxHeight.Text))
    Tempad.SecondLimit.LimitMode = 3 'catUpToPlaneLimit
    Tempad.SecondLimit.LimitingElement = selPlanarFace
    Tempad.Name = "TextPad"
    Else
    Set Tempad = tarPart.ShapeFactory.AddNewPocket(sketch1, Abs(Val(cbxHeight.Text)))
    Tempad.SecondLimit.LimitMode = 3 'catUpToPlaneLimit
    Tempad.SecondLimit.LimitingElement = selPlanarFace
    Tempad.Name = "TextPocket"
    End If
Tempad.IsThin = True
Dim Parameters2 'As Parameters
Set Parameters2 = tarPart.Parameters.SubList(Tempad, False)
Dim par 'As Parameter
For Each par In Parameters2
    Dim mainStr, subStrCN, subStrEN, position
    'Debug.Print par.Name
    mainStr = par.Name
    subStrCN = "厚薄": subStrEN = "ThickThin"
    position = InStr(1, mainStr, subStrCN, vbTextCompare)
    If position > 0 Then
        par.Value = Val(cbxThickness.Text) / 2
    End If
    position = InStr(1, mainStr, subStrEN, vbTextCompare)
    If position > 0 Then
        par.Value = Val(cbxThickness.Text) / 2
    End If
Next
End If
tarPart.Update
If Err.Number <> 0 Then
MsgBox "无法创建拉伸或切除特征，已保留文本草图！"
CATIA.ActiveDocument.Selection.Clear
CATIA.ActiveDocument.Selection.Add Tempad
CATIA.ActiveDocument.Selection.Delete
tarPart.Update
End If
End Sub

'###########为 TextBox 设置预览字体##########
'cbxFontName 条目格式为 "FontName (TrueType)"，Font.Name 只取空格前的部分。
'VBA TextBox.Font.Name 对纯 ASCII 字体名存在渲染异常（奇数长度时隔字回退到默认字体）。
'修复：若字体名为纯 ASCII，借用 StdFont 对象查出 GDI 本地化名称（中文名），再赋给 TextBox。
'中文字体名每字符占 2 字节，不受此 bug 影响，直接赋值即可。无需手动维护映射表。
Private Sub SetPreviewFont(tb As MSForms.TextBox, fontItemText As String)
    Dim spacePos As Integer
    spacePos = InStr(fontItemText, " ")
    Dim fontName As String
    fontName = IIf(spacePos > 0, Left(fontItemText, spacePos - 1), fontItemText)
    '判断是否为纯 ASCII 字体名（AscW 对所有字符均 < 128 则为纯 ASCII）
    Dim isAscii As Boolean
    isAscii = True
    Dim i As Integer
    For i = 1 To Len(fontName)
        If AscW(Mid(fontName, i, 1)) > 127 Then
            isAscii = False
            Exit For
        End If
    Next i
    If isAscii Then
        'ASCII 字体名：用 StdFont 查本地化名称，避免 TextBox 奇数长度渲染异常
        Dim tmpFont As New StdFont
        tmpFont.Name = fontName
        fontName = tmpFont.Name  '回读得到 GDI 解析的本地化名（通常为中文）
        Set tmpFont = Nothing
    End If
    tb.Font.Name = fontName
End Sub

'###########判断是否为单线字体（不含空格的字体名视为单线字体）##########
'约定：TrueType 等轮廓字体名格式为 "FontName (TrueType)"，包含空格；
'      单线字体（如 SICH、SSS4）名称中不含空格。
'后续新增字体只需在 UserForm_Activate 的 cbxFontName.AddItem 处添加即可，
'无需修改本函数及其他任何判断逻辑。
Private Function IsStrokeFont(fontItemText As String) As Boolean
    IsStrokeFont = (InStr(Trim(fontItemText), " ") = 0)
End Function


'####################保存用户设置##########################
Private Sub SaveConf()
On Error Resume Next
Dim sConfpath As String
Dim write1 'As Long
    '参数一： Section Name (节的名称)。
    '参数二： 节下面的项目名称。
    '参数三： 项目的内容。
    '参数四： ini配置文件的路径名称。
              
sConfpath = oCATVBA_Folder
write1 = WritePrivateProfileString("平面刻字", "文本输入类型", CStr(cbxInputType.ListIndex), sConfpath & "\Conf1.ini")

write1 = WritePrivateProfileString("平面刻字", "字体", CStr(cbxFontName.ListIndex), sConfpath & "\Conf1.ini")
write1 = WritePrivateProfileString("平面刻字", "字高", CStr(cbxFontSize.Text), sConfpath & "\Conf1.ini")
write1 = WritePrivateProfileString("平面刻字", "间距", CStr(cbxSpacing.Text), sConfpath & "\Conf1.ini")
write1 = WritePrivateProfileString("平面刻字", "凸起", CStr(cbxHeight.Text), sConfpath & "\Conf1.ini")
write1 = WritePrivateProfileString("平面刻字", "加厚", CStr(cbxThickness.Text), sConfpath & "\Conf1.ini")

write1 = WritePrivateProfileString("平面刻字", "布局", CStr(cbxLocation.ListIndex), sConfpath & "\Conf1.ini")
write1 = WritePrivateProfileString("平面刻字", "X", CStr(cbxX.Text), sConfpath & "\Conf1.ini")
write1 = WritePrivateProfileString("平面刻字", "Y", CStr(cbxY.Text), sConfpath & "\Conf1.ini")

write1 = WritePrivateProfileString("平面刻字", "镜像", CStr(cbxMirror.ListIndex), sConfpath & "\Conf1.ini")
End Sub

'####################读取用户设置##########################
Private Sub ReadConf()
Dim sConfpath As String
sConfpath = oCATVBA_Folder
Dim objFSO
Set objFSO = CreateObject("Scripting.FileSystemObject")
If Not objFSO.FileExists(sConfpath & "\Conf1.ini") Then
Exit Sub
End If
'---读取配置文件---
'On Error Resume Next
    Dim read_OK ' As Long
    Dim read2 As String
    read2 = String(255, 0)
    read_OK = GetPrivateProfileString("平面刻字", "文本输入类型", "0", read2, 256, sConfpath & "\Conf1.ini")
    cbxInputType.ListIndex = read2
    read2 = String(255, 0)
    read_OK = GetPrivateProfileString("平面刻字", "字体", "1", read2, 256, sConfpath & "\Conf1.ini")
    cbxFontName.ListIndex = read2
    read2 = String(255, 0)
    read_OK = GetPrivateProfileString("平面刻字", "字高", "3.5", read2, 256, sConfpath & "\Conf1.ini")
    cbxFontSize.Text = Val(read2)
    read2 = String(255, 0)
    read_OK = GetPrivateProfileString("平面刻字", "间距", "0.1", read2, 256, sConfpath & "\Conf1.ini")
    cbxSpacing.Text = read2
    read2 = String(255, 0)
    read_OK = GetPrivateProfileString("平面刻字", "凸起", "-0.3", read2, 256, sConfpath & "\Conf1.ini")
    cbxHeight.Text = read2
    read2 = String(255, 0) '因为设置了Enable，会出错
    read_OK = GetPrivateProfileString("平面刻字", "加厚", "0.3", read2, 256, sConfpath & "\Conf1.ini")
    cbxThickness.Text = Val(read2)
    
    read2 = String(255, 0)
    read_OK = GetPrivateProfileString("平面刻字", "布局", "0", read2, 256, sConfpath & "\Conf1.ini")
    cbxLocation.ListIndex = read2
    read2 = String(255, 0)
    read_OK = GetPrivateProfileString("平面刻字", "X", "0", read2, 256, sConfpath & "\Conf1.ini")
    cbxX.Text = read2
    read2 = String(255, 0)
    read_OK = GetPrivateProfileString("平面刻字", "Y", "0", read2, 256, sConfpath & "\Conf1.ini")
    cbxY.Text = read2
    
    read2 = String(255, 0)
    read_OK = GetPrivateProfileString("平面刻字", "镜像", "0", read2, 256, sConfpath & "\Conf1.ini")
    cbxMirror.ListIndex = read2
End Sub

'####################窗体启动##########################
Private Sub UserForm_Activate()
    '防止窗体多次激活时重复添加列表项
    If cbxFontName.ListCount > 0 Then
        GoTo SkipInit
    End If

    cbxInputType.AddItem "输入文本": cbxInputType.AddItem "用零件编号刻字": cbxInputType.AddItem "用几何体名称刻字"
    cbxInputType.ListIndex = 0
    cbxInputType.Style = fmStyleDropDownList
    
    '--- 可选字体列表 ---
    '轮廓字体（TrueType）：名称格式须含空格，如 "FontName (TrueType)"
    '单线字体：名称中不含空格，如 SICH、SSS4
    '后续新增字体只需在此处追加 AddItem，无需修改其他代码
    cbxFontName.AddItem "DengXian (TrueType)"
    cbxFontName.AddItem "KaiTi (TrueType)"
    cbxFontName.AddItem "SimSun (TrueType)"
    cbxFontName.AddItem "FangSong (TrueType)"
    cbxFontName.AddItem "ChangFangSong (TrueType)"
    cbxFontName.AddItem "SICH"
    cbxFontName.AddItem "SSS4"
    '--- 字体列表结束 ---
    cbxFontName.ListIndex = 1
    cbxFontName.Style = fmStyleDropDownList
    
    cbxFontSize.AddItem "2.5": cbxFontSize.AddItem "3.5": cbxFontSize.AddItem "5.0": cbxFontSize.AddItem "7.0": cbxFontSize.AddItem "10.0"
    cbxFontSize.AddItem "14.0": cbxFontSize.AddItem "18.0": cbxFontSize.AddItem "20.0"
    cbxFontSize.ListIndex = 2
    
    cbxSpacing.AddItem "0": cbxSpacing.AddItem "0.1": cbxSpacing.AddItem "0.2": cbxSpacing.AddItem "0.5": cbxSpacing.AddItem "0.8": cbxSpacing.AddItem "1.0"
    cbxSpacing.ListIndex = 1
    
    cbxHeight.AddItem "-1.0": cbxHeight.AddItem "-0.8": cbxHeight.AddItem "-0.5": cbxHeight.AddItem "-0.3": cbxHeight.AddItem "-0.1"
    cbxHeight.AddItem "0"
    cbxHeight.AddItem "0.1": cbxHeight.AddItem "0.3": cbxHeight.AddItem "0.5": cbxHeight.AddItem "0.8": cbxHeight.AddItem "1.0"
    cbxHeight.ListIndex = 3
    
    cbxThickness.AddItem "0.2": cbxThickness.AddItem "0.3": cbxThickness.AddItem "0.5": cbxThickness.AddItem "0.8": cbxThickness.AddItem "1.0"
    cbxThickness.ListIndex = 1
    
    cbxLocation.AddItem "自动居中(自动判断）": cbxLocation.AddItem "X居中": cbxLocation.AddItem "XY距离"
    cbxLocation.ListIndex = 1
    cbxLocation.Style = fmStyleDropDownList
    
    cbxX.AddItem "0": cbxX.AddItem "4": cbxX.AddItem "8": cbxX.AddItem "10": cbxX.AddItem "12": cbxX.AddItem "15": cbxX.AddItem "20": cbxX.AddItem "30"
    cbxX.ListIndex = 0
    
    cbxY.AddItem "0": cbxY.AddItem "4": cbxY.AddItem "8": cbxY.AddItem "10": cbxY.AddItem "12": cbxY.AddItem "15": cbxY.AddItem "20": cbxY.AddItem "30"
    cbxY.ListIndex = 0
    
    cbxMirror.AddItem "不镜像": cbxMirror.AddItem "水平翻转": cbxMirror.AddItem "垂直翻转": cbxMirror.AddItem "水平垂直翻转"
    cbxMirror.ListIndex = 0
    cbxMirror.Style = fmStyleDropDownList

    ReadConf
SkipInit:
    On Error Resume Next
    SetPreviewFont txtInput, cbxFontName.Text
    SetPreviewFont txtSpecial, cbxFontName.Text
    On Error GoTo 0
    txtInput.Font.Size = Val(cbxFontSize.Text) * 2.8346 + 4 '转换是1 毫米 ≈ 2.8346 磅，+4是为了界面好阅读
End Sub

Private Sub UserForm_QueryClose(Cancel As Integer, CloseMode As Integer)
SaveConf
End Sub
' 向量减法
Sub VectorSubtract(ByRef v1() As Double, ByRef v2() As Double, ByRef Result() As Double)
    Result(0) = v1(0) - v2(0)
    Result(1) = v1(1) - v2(1)
    Result(2) = v1(2) - v2(2)
End Sub

' 向量叉乘
Sub CrossProduct(ByRef v1() As Double, ByRef v2() As Double, ByRef Result() As Double)
    Result(0) = v1(1) * v2(2) - v1(2) * v2(1)
    Result(1) = v1(2) * v2(0) - v1(0) * v2(2)
    Result(2) = v1(0) * v2(1) - v1(1) * v2(0)
End Sub

' 向量点乘
Function dotProduct(ByRef v1() As Double, ByRef v2() As Double) As Double
    dotProduct = v1(0) * v2(0) + v1(1) * v2(1) + v1(2) * v2(2)
End Function

' 向量归一化
Sub NormalizeVector(ByRef v() As Double)
    Dim length As Double
    length = Sqr(v(0) * v(0) + v(1) * v(1) + v(2) * v(2))
    
    If length > 0 Then
        v(0) = v(0) / length
        v(1) = v(1) / length
        v(2) = v(2) / length
    End If
End Sub
' ############计算用户坐标系############
Sub CalculateUserCoordinateSystem( _
    ByRef A() As Double, _
    ByRef B() As Double, _
    ByRef C() As Double, _
    ByRef z() As Double, _
    ByRef vUp() As Double, _
    ByRef Cnew() As Double, _
    ByRef Origin() As Double, _
    ByRef XAxis() As Double, _
    ByRef YAxis() As Double, _
    ByRef ZAxis() As Double)
    
    ' 首先尝试以A为原点
    Dim success As Boolean
    
    ' 初始化数组
    If Not IsArray(Origin) Then ReDim Origin(2)
    If Not IsArray(XAxis) Then ReDim XAxis(2)
    If Not IsArray(YAxis) Then ReDim YAxis(2)
    If Not IsArray(ZAxis) Then ReDim ZAxis(2)
    
    success = TryCalculateSystem(A, B, C, z, vUp, Cnew, Origin, XAxis, YAxis, ZAxis)
    
    ' 如果以A为原点失败，则尝试以B为原点
    If Not success Then
        success = TryCalculateSystem(B, A, C, z, vUp, Cnew, Origin, XAxis, YAxis, ZAxis)
    End If
    
    ' 如果两次尝试都失败，抛出错误
    If Not success Then
        Err.Raise 5, "CalculateUserCoordinateSystem", "无法创建符合条件的用户坐标系"
    End If
End Sub

' ############尝试以给定的原点计算用户坐标系############
Function TryCalculateSystem( _
    ByRef Origin() As Double, _
    ByRef OtherEnd() As Double, _
    ByRef C() As Double, _
    ByRef z() As Double, _
    ByRef vUp() As Double, _
    ByRef Cnew() As Double, _
    ByRef OutOrigin() As Double, _
    ByRef OutXAxis() As Double, _
    ByRef OutYAxis() As Double, _
    ByRef OutZAxis() As Double) As Boolean
    
    ' 设置原点
    Dim i As Integer
    For i = 0 To 2
        OutOrigin(i) = Origin(i)
    Next
    
    ' 计算X轴方向（从原点到另一个端点的向量）
    Dim xDir(2) As Double
    VectorSubtract OtherEnd, Origin, xDir
    NormalizeVector xDir
    
    ' 复制X轴
    For i = 0 To 2
        OutXAxis(i) = xDir(i)
    Next
    
    ' 计算从原点到点C的向量
    Dim cDir(2) As Double
    VectorSubtract C, Origin, cDir
    
    ' 计算初始Z轴方向（X轴和C方向的叉乘）
    Dim zDir(2) As Double
    CrossProduct OutXAxis, cDir, zDir
    
    ' 检查Z轴是否有效（如果为零向量，表示三点共线）
    Dim zLength As Double
    zLength = Sqr(zDir(0) * zDir(0) + zDir(1) * zDir(1) + zDir(2) * zDir(2))
    If zLength < 0.0001 Then
        TryCalculateSystem = False
        Exit Function
    End If
    
    ' 归一化Z轴
    NormalizeVector zDir
    
    ' 检查Z轴与参考Z方向的点积（确保夹角不大于90度）
    Dim zDotProduct As Double  ' 重命名变量，避免与函数名冲突
    zDotProduct = dotProduct(zDir, z)  ' 正确调用函数，移除括号
    
    ' 如果点积为负，说明夹角大于90度，需要反转Z轴方向
    If zDotProduct < 0 Then
        For i = 0 To 2
            zDir(i) = -zDir(i)
        Next
    End If
    
    ' 复制Z轴
    For i = 0 To 2
        OutZAxis(i) = zDir(i)
    Next
    
    ' 计算Y轴方向（Z轴和X轴的叉乘，确保右手定则）
    CrossProduct OutZAxis, OutXAxis, OutYAxis
    
    '检查Y轴方向是否与 vUp方向夹角小于90度
    
      Dim yDotProduct As Double  ' 重命名变量，避免与函数名冲突
    yDotProduct = dotProduct(OutYAxis, vUp)  ' 正确调用函数，移除括号
    
    ' 如果点积为负，说明夹角大于90度，需要反转Y轴方向
    ' 如果点积为非负，说明夹角小于90度，坐标系正确
    If yDotProduct >= 0 Then
        ' 检查另一个端点在用户坐标系中的X坐标是否为正
        Dim otherEndXCoord As Double
        otherEndXCoord = dotProduct(xDir, OutXAxis)
        If otherEndXCoord > 0 Then
            TryCalculateSystem = True
            ' 计算点C在用户坐标系中的XY坐标
            Cnew(0) = dotProduct(cDir, OutXAxis): Cnew(1) = dotProduct(cDir, OutYAxis)
            Exit Function
        End If
    End If

    ' 如果不满足条件，返回失败
    TryCalculateSystem = False
End Function

'############ 判断两个单位向量是否平行（方向相同或相反）############
Function AreUnitVectorsParallel(t1() As Double, t2() As Double) As Boolean
    ' 计算点积
    Dim dotProduct1 As Double
    dotProduct1 = dotProduct(t1, t2)
    
    ' 设置一个小的容差值，处理浮点数精度问题
    Dim tolerance As Double
    tolerance = 0.000001
    
    ' 如果点积的绝对值接近1，则认为向量平行
    AreUnitVectorsParallel = (Abs(Abs(dotProduct1) - 1) < tolerance)
End Function

Attribute VB_Name = "TextOnPlanarFace_3D"
Sub CATMain()
TextOnPlanarFace.Show vbModeless
TextOnPlanarFace.Left = TextOnPlanarFace.Left * 2
End Sub

Attribute VB_Name = "ThreadColor_3D"
Option Explicit

Const exeprg = "Thread_Color_3D.exe"

Sub CATMain()
On Error Resume Next
Shell oCATVBA_Folder.Path & "\" & exeprg, vbNormalFocus
If Err.Number <> 0 Then
MsgBox "无法调用" & exeprg & vbCrLf & "请确认" & exeprg & "存在于" & oCATVBA_Folder.Path, vbQuestion, "CATIA工具箱"
End If
End Sub

Attribute VB_Name = "TitleBlockProperties"
Attribute VB_Base = "0{720F45DA-FDD9-4A27-88D3-5B811B475DC8}{727B0EF9-680F-4D59-8117-4A7B55C6FACB}"
Attribute VB_GlobalNameSpace = False
Attribute VB_Creatable = False
Attribute VB_PredeclaredId = True
Attribute VB_Exposed = False
Attribute VB_TemplateDerived = False
Attribute VB_Customizable = False
Option Explicit
Private Sub btnOK_Click()

    ModScaniaPro CATIA.ActiveDocument.Product
    Unload Me

End Sub

Sub ModScaniaPro(oPrd As Object)
Dim crl As Object
Dim j As Integer
Dim strParam As Object
Dim oUserPara As Object 'Parameters
Set oUserPara = oPrd.UserRefProperties
    For j = 1 To oUserPara.Count
    oUserPara.Remove (1)
    Next
    
    For Each crl In TitleBlockProperties.Controls
        If TypeName(crl) = "TextBox" Then
        '需检查不属于固有属性 "PartNumber", "Revision", "Definition", "Nomenclature", "Source", "DescriptionRef"
        Select Case crl.Name
               Case "PartNumber"
                    oPrd.PartNumber = crl.Text
               Case "Revision"
                    oPrd.Revision = crl.Text
               Case "Definition"
                    oPrd.Definition = crl.Text
               Case "Nomenclature"
                     oPrd.Nomenclature = crl.Text
               Case "DescriptionRef"
                    oPrd.DescriptionRef = crl.Text
               Case Else
                Set strParam = oUserPara.CreateString(crl.Name, crl.Text)
        End Select
        End If
    Next
End Sub

Attribute VB_Name = "View_Name_GB_2D"
Option Explicit

Sub CATMain()
    'On Error Resume Next
    IntCATIA
    Dim oDocument
    Set oDocument = CATIA.ActiveDocument
    If TypeName(oDocument) <> "DrawingDocument" Then
        MsgBox "此命令的功能是将工程图的剖视图，断面视图，细节视图，向视图，轴测视图按中国国标命名，因此需要在工程制图环境下运行！" & vbCrLf & _
                     "运行此宏命令后，在工程制图的激活视图中单击鼠标左键以将视图名称放置在指定位置即可！" & vbCrLf & vbCrLf & _
                     "请在工程制图环境下运行此命令，现在退出...", vbInformation, "CATIA工具箱”"
        Exit Sub
        
    End If
    Dim oDrawingDoc2 As Object 'DrawingDocument
    Set oDrawingDoc2 = oDocument
    
    Dim oDrwSheet As Object
    Set oDrwSheet = oDocument.Sheets.ActiveSheet
    
    Dim oDrwViews As Object 'DrawingViews
    Set oDrwViews = oDrwSheet.Views
    
    Dim oDrwView As Object 'DrawingView
    Set oDrwView = oDrwViews.ActiveView
    
    Dim oDrawingTexts As Object 'DrawingTexts
    Set oDrawingTexts = oDrwView.Texts
    
    Dim oDrawingText As Object 'DrawingText
    
    Dim iParameters As Object 'Parameters
    Set iParameters = oDrawingDoc2.Parameters
    Dim iParameter As Object 'Parameter
    
    Dim MyPrefix As String, MyIdent As String, MySuffix As String
    Dim oPrefix As String, oIdent As String, oSuffix As String
    Dim DrawingWindowLocation(1)
    Dim Status
    Dim itext As String

    Dim ViewNo As Integer
    Dim FrontViewScale
    
    If oDrwSheet.Views.Count <> 0 Then
        For ViewNo = 1 To oDrwSheet.Views.Count
            If oDrwSheet.Views.Item(ViewNo).ViewType = 1 Then 'catViewFront
                FrontViewScale = oDrwSheet.Views.Item(ViewNo).Scale2
                GoTo Skip
            Else
                FrontViewScale = 0
            End If
        Next ViewNo
    End If
    
Skip:
    If oDrwView.ViewType = 9 Or oDrwView.ViewType = 10 Then      '>>>>剖视图和断面视图<<<<<
        Status = oDocument.Indicate2D("在当前激活视图中单击鼠标左键以将视图名称放置在指定位置", DrawingWindowLocation)
        If Status = "Cancel" Then Exit Sub
                    
        oDrwView.GetViewName MyPrefix, MyIdent, MySuffix
    
        oPrefix = ""
        oSuffix = ""
        oDrwView.SetViewName oPrefix, MyIdent, oSuffix
        
        If oDrwView.Scale2 <> FrontViewScale Then
        itext = vbLf
        Else: itext = ""
        End If
        
        Set oDrawingText = oDrawingTexts.Add(itext, DrawingWindowLocation(0), DrawingWindowLocation(1))
        
        Set iParameter = iParameters.Item(oDrwSheet.Name & "\" & oDrwView.Name & "\Name")
        oDrawingText.InsertVariable 1, 0, iParameter
        
        If oDrwView.Scale2 <> FrontViewScale Then
        oDrwView.InsertViewScale Len(oDrawingText.Text) + 1, oDrawingText
        End If
        
        oDrawingText.SetParameterOnSubString 0, 0, 0, 1                           '设为粗体catBold
        
        If oDrwView.Scale2 <> FrontViewScale Then
        oDrawingText.SetParameterOnSubString 2, 0, Len(oDrwView.Name) + 1, 1 '名称部分加下划线
        End If
        
        oDrawingText.SetParameterOnSubString 13, 0, 0, 2                      '设为右侧对齐2,居中1,靠左0
        oDrawingText.SetFontSize 0, 0, 3.5                                              '字体改为3.5
        
    ElseIf oDrwView.ViewType = 11 Then        '>>>>细节视图<<<<<catViewDetail
        
        Dim i As Integer
        Static sequence As Integer
        sequence = 0
        Dim SequenceOfView As Integer
        
        If oDrwSheet.Views.Count <> 0 Then
            For i = 1 To oDrwSheet.Views.Count
            If oDrwSheet.Views.Item(i).ViewType = 11 Then
            sequence = sequence + 1
                If oDrwSheet.Views.Item(i).Name = oDrwView.Name Then
                SequenceOfView = sequence
                End If
            End If
            Next i
        End If
        
        Status = oDocument.Indicate2D("在当前激活视图中单击鼠标左键以将视图名称放置在指定位置", DrawingWindowLocation)
        If Status = "Cancel" Then Exit Sub
        
        Select Case SequenceOfView
        Case 1
            oIdent = "Ⅰ"
        Case 2
            oIdent = "Ⅱ"
        Case 3
            oIdent = "Ⅲ"
        Case 4
            oIdent = "Ⅳ"
        Case 5
            oIdent = "Ⅴ"
        Case 6
            oIdent = "Ⅵ"
        Case 7
            oIdent = "Ⅶ"
        Case 8
            oIdent = "Ⅷ"
        Case 9
            oIdent = "Ⅸ"
        Case 10
            oIdent = "Ⅹ"
        Case 11
            oIdent = "Ⅺ"
        Case 12
            oIdent = "Ⅻ"
        End Select
        
        oPrefix = " "
        oSuffix = " "
        oDrwView.SetViewName oPrefix, oIdent, oSuffix
        
        If oDrwView.Scale2 <> FrontViewScale Then
        itext = vbLf
        Else: itext = ""
        End If
                
        Set oDrawingText = oDrawingTexts.Add(itext, DrawingWindowLocation(0), DrawingWindowLocation(1))
        
        Set iParameter = iParameters.Item(oDrwSheet.Name & "\" & oDrwView.Name & "\Name")
        oDrawingText.InsertVariable 1, 0, iParameter
        
        If oDrwView.Scale2 <> FrontViewScale Then
        oDrwView.InsertViewScale Len(oDrawingText.Text) + 1, oDrawingText
        End If
    
        oDrawingText.SetParameterOnSubString 0, 0, 0, 1
        
        If oDrwView.Scale2 <> FrontViewScale Then
        oDrawingText.SetParameterOnSubString 2, 0, Len(oDrwView.Name) + 1, 1
        End If
        
        oDrawingText.SetParameterOnSubString 13, 0, 0, 2
        oDrawingText.SetFontSize 0, 0, 3.5

    ElseIf oDrwView.ViewType = 8 Then     '>>>>轴测视图<<<<<
        Status = oDocument.Indicate2D("在当前激活视图中单击鼠标左键以将视图名称放置在指定位置", DrawingWindowLocation)

        If Status = "Cancel" Then Exit Sub
        
        oPrefix = "轴测视图 / ISOMETRIC VIEW"
        oIdent = ""
        oSuffix = ""
        oDrwView.SetViewName oPrefix, oIdent, oSuffix
        
        If oDrwView.Scale2 <> FrontViewScale Then
        itext = vbLf
        Else: itext = ""
        End If
        
        Set oDrawingText = oDrawingTexts.Add(itext, DrawingWindowLocation(0), DrawingWindowLocation(1))
        
        Set iParameter = iParameters.Item(oDrwSheet.Name & "\" & oDrwView.Name & "\Name")
        oDrawingText.InsertVariable 1, 0, iParameter
        
        If oDrwView.Scale2 <> FrontViewScale Then
        oDrwView.InsertViewScale Len(oDrawingText.Text) + 1, oDrawingText
        End If
    
        oDrawingText.SetParameterOnSubString 0, 0, 0, 1
        
        If oDrwView.Scale2 <> FrontViewScale Then
        oDrawingText.SetParameterOnSubString 2, 0, Len(oDrwView.Name) + 1, 1
        End If
        
        oDrawingText.SetParameterOnSubString 13, 0, 0, 1
        oDrawingText.SetFontSize 0, 0, 3.5
        
    ElseIf oDrwView.ViewType = 7 Then    '>>>>向视图<<<<<
        Status = oDocument.Indicate2D("在当前激活视图中单击鼠标左键以将视图名称放置在指定位置", DrawingWindowLocation)
        If Status = "Cancel" Then Exit Sub
        
        oDrwView.GetViewName MyPrefix, MyIdent, MySuffix

        oPrefix = "  "
        oIdent = ""
        oSuffix = "  "
        oDrwView.SetViewName oPrefix, MyIdent, oSuffix
        
        If oDrwView.Scale2 <> FrontViewScale Then
        itext = vbLf
        Else: itext = ""
        End If
        
        Set oDrawingText = oDrawingTexts.Add(itext, DrawingWindowLocation(0), DrawingWindowLocation(1))
        
        Set iParameter = iParameters.Item(oDrwSheet.Name & "\" & oDrwView.Name & "\Name")
        oDrawingText.InsertVariable 1, 0, iParameter
        
        If oDrwView.Scale2 <> FrontViewScale Then
        oDrwView.InsertViewScale Len(oDrawingText.Text) + 1, oDrawingText
        End If
    
        oDrawingText.SetParameterOnSubString 0, 0, 0, 1
        
        If oDrwView.Scale2 <> FrontViewScale Then
        oDrawingText.SetParameterOnSubString 2, 0, Len(oDrwView.Name) + 1, 1
        End If
        
        oDrawingText.SetParameterOnSubString 13, 0, 0, 2
        oDrawingText.SetFontSize 0, 0, 3.5

    ElseIf oDrwView.ViewType = 15 Then  '>>>>展开视图<<<<<
        Status = oDocument.Indicate2D("在当前激活视图中单击鼠标左键以将视图名称放置在指定位置", DrawingWindowLocation)

        If Status = "Cancel" Then Exit Sub
        
        oPrefix = "展开视图 / UNFOLDED VIEW"
        oIdent = ""
        oSuffix = ""
        oDrwView.SetViewName oPrefix, oIdent, oSuffix
        
        If oDrwView.Scale2 <> FrontViewScale Then
        itext = vbLf
        Else: itext = ""
        End If
        
        Set oDrawingText = oDrawingTexts.Add(itext, DrawingWindowLocation(0), DrawingWindowLocation(1))
        
        Set iParameter = iParameters.Item(oDrwSheet.Name & "\" & oDrwView.Name & "\Name")
        oDrawingText.InsertVariable 1, 0, iParameter
        
        If oDrwView.Scale2 <> FrontViewScale Then
        oDrwView.InsertViewScale Len(oDrawingText.Text) + 1, oDrawingText
        End If
    
        oDrawingText.SetParameterOnSubString 0, 0, 0, 1
        
        If oDrwView.Scale2 <> FrontViewScale Then
        oDrawingText.SetParameterOnSubString 2, 0, Len(oDrwView.Name) + 1, 1
        End If
        
        oDrawingText.SetParameterOnSubString 13, 0, 0, 1
        oDrawingText.SetFontSize 0, 0, 3.5

    
    End If
        
    sequence = 0
    
End Sub

Attribute VB_Name = "模块1"
Sub CATMain()

Dim bSTR1 As String
bSTR1 = CATIA.Name

Dim bSTR2 As String
bSTR2 = CATIA.Name

Dim bSTR3 As String
bSTR3 = CATIA.Name

Dim bSTR4 As String
bSTR4 = CATIA.Name

End Sub
