Attribute VB_Name = "TextOnPlanarFace"
Attribute VB_Base = "0{25A926F5-2FA2-4398-8F79-710675760A84}{A338D7F6-0826-422A-B2D8-41F17048E705}"
Attribute VB_GlobalNameSpace = False
Attribute VB_Creatable = False
Attribute VB_PredeclaredId = True
Attribute VB_Exposed = False
Attribute VB_TemplateDerived = False
Attribute VB_Customizable = False

Option Explicit
#If VBA7 Then
Private Declare PtrSafe Function ShellExecute Lib "shell32.dll" Alias "ShellExecuteA" (ByVal hwnd As LongPtr, ByVal lpOperation As String, ByVal lpFile As String, ByVal lpParameters As String, ByVal lpDirectory As String, ByVal nShowCmd As Long) As LongPtr
Private Declare PtrSafe Function GetPrivateProfileString Lib "kernel32" Alias "GetPrivateProfileStringA" (ByVal lpApplicationName As String, ByVal lpKeyName As Any, ByVal lpDefault As String, ByVal lpReturnedString As String, ByVal nSize As LongPtr, ByVal lpFileName As String) As LongPtr
Private Declare PtrSafe Function WritePrivateProfileString Lib "kernel32" Alias "WritePrivateProfileStringA" (ByVal lpApplicationName As String, ByVal lpKeyName As Any, ByVal lpString As Any, ByVal lpFileName As String) As LongPtr
#Else
Private Declare Function ShellExecute Lib "shell32.dll" Alias "ShellExecuteA" (ByVal hwnd As Long, ByVal lpOperation As String, ByVal lpFile As String, ByVal lpParameters As String, ByVal lpDirectory As String, ByVal nShowCmd As Long) As Long
Private Declare Function GetPrivateProfileString Lib "kernel32" Alias "GetPrivateProfileStringA" (ByVal lpApplicationName As String, ByVal lpKeyName As Any, ByVal lpDefault As String, ByVal lpReturnedString As String, ByVal nSize As Long, ByVal lpFileName As String) As Long
Private Declare Function WritePrivateProfileString Lib "kernel32" Alias "WritePrivateProfileStringA" (ByVal lpApplicationName As String, ByVal lpKeyName As Any, ByVal lpString As Any, ByVal lpFileName As String) As Long
#End If
Const cmdCaption = "开始刻字"
Const cmdBackColor = &H8000000F
Const cmdBackColorRuning = &HFFFF&
Private m_colHandlers As Collection
Dim selPlanarFace, selEdge As Object
Dim tarBody As Body: Dim tarHybridBody As HybridBody: Dim tarPart As Part
Dim sketchVariantOfDouble(8) '草图方向，也是计算的新坐标系
Dim CoGCoordInUserAxis(1) As Double '所选平面重心点C在用户坐标系中的坐标，可正可负
Dim xCenter As Double '所选X线段的半，用于X居中Y输入的情况，永远为正
Dim extrueSketch As Boolean
Dim text2write As String

'####################执行按钮##########################
Private Sub cmdRun_Click()
If CATIA.ActiveDocument Is Nothing Then Exit Sub
Set oActDoc = CATIA.ActiveDocument
If TypeName(oActDoc) <> "PartDocument" Then
    MsgBox "此命令只能在零件设计模块下运行", , "臭豆腐工具箱CATIA版|平面刻字"
    Exit Sub
End If

If txtInput.Text = "" Then
    MsgBox "要刻字的内容为空！请输入要刻字的内容再运行！"
    Exit Sub
End If

Set selPlanarFace = Nothing: Set selEdge = Nothing
Set tarBody = Nothing: Set tarPart = Nothing
CoGCoordInUserAxis(0) = 0: CoGCoordInUserAxis(1) = 0
text2write = ""
If Val(cbxHeight.Text) = 0 Then
extrueSketch = False
Else
extrueSketch = True
End If

Dim A(2) As Double, B(2) As Double, C(2) As Double, z(2) As Double, yUp(2) As Double
Dim Origin(2) As Double, XAxis(2) As Double, YAxis(2) As Double, ZAxis(2) As Double

cmdRun.Caption = "请选择刻字平面"
cmdRun.BackColor = cmdBackColorRuning
Set selPlanarFace = Sel("PlanarFace")
If selPlanarFace Is Nothing Then
    cmdRun.Caption = cmdCaption
    cmdRun.BackColor = cmdBackColor
    Exit Sub
End If
cmdRun.Caption = "请选择平面内的线段作为X轴"
Set selEdge = Sel("RectilinearTriDimFeatEdge", "RectilinearBiDimFeatEdge", "RectilinearMonoDimFeatEdge")
If selEdge Is Nothing Then
    cmdRun.Caption = cmdCaption
    cmdRun.BackColor = cmdBackColor
    Exit Sub
End If

'取得平面所属于的Body或几何图形集以及Part
Dim nodeType
Set nodeType = selPlanarFace
Do While (TypeName(nodeType) <> "PartDocument")
    Set nodeType = nodeType.Parent
    If TypeName(nodeType) = "Body" Then
    Set tarBody = nodeType
    End If
    If TypeName(nodeType) = "HybridBody" Then
    Set tarHybridBody = nodeType
    End If
    If TypeName(nodeType) = "Part" Then
    Set tarPart = nodeType
    End If
Loop
If tarBody Is Nothing Then
   If MsgBox("所选平面不属于任何实体！只能创建草图不能创建凸凹字，需要继续吗?", vbQuestion + vbYesNo) = vbNo Then
        cmdRun.Caption = cmdCaption
        cmdRun.BackColor = cmdBackColor
        Exit Sub
   End If
   extrueSketch = False
   tarPart.InWorkObject = tarHybridBody
Else
   tarPart.InWorkObject = tarBody
End If

'取得平面法向向量，可能向内也可能向外
Dim tX(2): Dim tY(2)
selPlanarFace.GetFirstAxis tX
selPlanarFace.GetSecondAxis tY
Dim tX1(2) As Double: Dim tY1(2) As Double: Dim tZ(2) As Double
tX1(0) = tX(0): tX1(1) = tX(1): tX1(2) = tX(2)
tY1(0) = tY(0): tY1(1) = tY(1): tY1(2) = tY(2)
CrossProduct tX1, tY1, tZ
NormalizeVector tZ
'取得平面质心作为点C
Dim objSPAWkb
Set objSPAWkb = CATIA.ActiveDocument.GetWorkbench("SPAWorkbench")
Dim objRef As Object
Dim objMeasurable
'Set objRef = oActDoc.Part.CreateReferenceFromObject(selPlanarFace)
Set objMeasurable = objSPAWkb.GetMeasurable(selPlanarFace)
Dim C0(2)
objMeasurable.GetCOG C0
C(0) = C0(0): C(1) = C0(1): C(2) = C0(2)
'Debug.Print "平面重心C: (" & C(0) & ", " & C(1) & ", " & C(2) & ")"

'从屏幕由内往外方向作为用户坐标系Z轴参考，屏幕向上方向作为用户坐标系Y轴参考
Dim ActViewer As Viewer3D
Dim varViewer As Variant
Set ActViewer = CATIA.ActiveWindow.ActiveViewer
Set varViewer = ActViewer
' get viewpoint
Dim varViewpoint As Variant
Dim ActViewpoint As Viewpoint3D
Set ActViewpoint = ActViewer.Viewpoint3D
Set varViewpoint = ActViewpoint
Dim vDirectionSight(2) As Variant
varViewpoint.GetSightDirection vDirectionSight
z(0) = vDirectionSight(0) * (-1): z(1) = vDirectionSight(1) * (-1): z(2) = vDirectionSight(2) * (-1)

'Debug.Print "从屏幕由内往外方向: (" & Z(0) & ", " & Z(1) & ", " & Z(2) & ")"
Dim vDirectionUp(2) As Variant
varViewpoint.GetUpDirection vDirectionUp
yUp(0) = vDirectionUp(0): yUp(1) = vDirectionUp(1): yUp(2) = vDirectionUp(2)

Dim pointOnCurve(8)
Set objRef = Nothing: Set objMeasurable = Nothing
Set objMeasurable = objSPAWkb.GetMeasurable(selEdge)
objMeasurable.GetPointsOnCurve pointOnCurve
A(0) = pointOnCurve(0): A(1) = pointOnCurve(1): A(2) = pointOnCurve(2)
B(0) = pointOnCurve(6): B(1) = pointOnCurve(7): B(2) = pointOnCurve(8)

xCenter = objMeasurable.length / 2

' 计算用户坐标系
On Error GoTo ErrorHandler
CalculateUserCoordinateSystem A, B, C, z, yUp, CoGCoordInUserAxis, Origin, XAxis, YAxis, ZAxis
If AreUnitVectorsParallel(tZ, ZAxis) = False Then
    MsgBox "所选直线边不属于所选平面！刻字终止！", vbExclamation + vbOKOnly
    cmdRun.Caption = cmdCaption
    cmdRun.BackColor = cmdBackColor
    Exit Sub
End If

sketchVariantOfDouble(0) = Origin(0): sketchVariantOfDouble(1) = Origin(1): sketchVariantOfDouble(2) = Origin(2)
sketchVariantOfDouble(3) = XAxis(0): sketchVariantOfDouble(4) = XAxis(1): sketchVariantOfDouble(5) = XAxis(2)
sketchVariantOfDouble(6) = YAxis(0): sketchVariantOfDouble(7) = YAxis(1): sketchVariantOfDouble(8) = YAxis(2)

'刻字内容
Select Case cbxInputType.ListIndex
    Case 0
        text2write = txtInput.Text
    Case 1
        text2write = tarPart.Parent.Product.PartNumber
    Case 2
        If tarBody Is Nothing Then
        text2write = tarHybridBody.Name
        Else
        text2write = tarBody.Name
        End If
    Case Else
        text2write = txtInput.Text
End Select
    
CreateText text2write
cmdRun.Caption = cmdCaption
cmdRun.BackColor = cmdBackColor
Exit Sub
ErrorHandler:
    MsgBox "错误: " & Err.Description, vbExclamation
    cmdRun.Caption = cmdCaption
    cmdRun.BackColor = cmdBackColor
End Sub

'##############布局更改时显示或隐藏XY##################
Private Sub cbxLocation_Click()
Select Case cbxLocation.ListIndex
    Case 0
        cbxX.Enabled = False: cbxY.Enabled = False
        cbxX.Visible = False: cbxY.Visible = False
        txtInput.TextAlign = fmTextAlignCenter
    Case 1
        cbxX.Enabled = False: cbxY.Enabled = True
        cbxX.Visible = False: cbxY.Visible = True
        txtInput.TextAlign = fmTextAlignCenter
    Case 2
        cbxX.Enabled = True: cbxY.Enabled = True
        cbxX.Visible = True: cbxY.Visible = True
        txtInput.TextAlign = fmTextAlignLeft
End Select
End Sub

'####################切换字体##########################
Private Sub cbxFontName_Click()
Select Case cbxFontName.ListIndex
Case 0
    cbxThickness.Enabled = False: cbxThickness.Visible = False
    txtInput.Font.Name = StringBeforeSpace(cbxFontName.Text)
    txtSpecial.Font.Name = StringBeforeSpace(cbxFontName.Text)
Case 1
    cbxThickness.Enabled = False: cbxThickness.Visible = False
    txtInput.Font.Name = StringBeforeSpace(cbxFontName.Text)
    txtSpecial.Font.Name = StringBeforeSpace(cbxFontName.Text)
Case 2
    cbxThickness.Enabled = False: cbxThickness.Visible = False
    txtInput.Font.Name = StringBeforeSpace(cbxFontName.Text)
txtSpecial.Font.Name = StringBeforeSpace(cbxFontName.Text)
Case 3
    cbxThickness.Enabled = True: cbxThickness.Visible = True
Case 4
    cbxThickness.Enabled = True: cbxThickness.Visible = True
End Select
End Sub
'####################切换输入类型##########################
Private Sub cbxInputType_Click()
If cbxInputType.ListIndex = 0 Then
txtInput.Enabled = True: txtInput.Text = ""
Else
txtInput.Text = "--自动提取，无需输入--": txtInput.Enabled = False
End If
End Sub
'####################切换字高##########################
Private Sub cbxFontSize_Click()
txtInput.Font.Size = Val(cbxFontSize.Text) * 2.8346 + 4
End Sub
'####################选择字高##########################
Private Sub cbxFontSize_LostFocus()
txtInput.Font.Size = Val(cbxFontSize.Text) * 2.8346 + 4
End Sub

'####################选择对象##########################
Public Function Sel(ObjType As String, Optional ObjType2 As String, Optional ObjType3 As String)
Dim S2, InputObjectType(), Status, NotSel, obj, Picked
Set S2 = CATIA.ActiveDocument.Selection
S2.Clear

If ObjType2 = "" Then
        ReDim InputObjectType(0)
        InputObjectType(0) = ObjType
        ElseIf ObjType3 = "" Then
                ReDim InputObjectType(1)
                InputObjectType(0) = ObjType
                InputObjectType(1) = ObjType2
                Else
                    ReDim InputObjectType(2)
                    InputObjectType(0) = ObjType
                    InputObjectType(1) = ObjType2
                    InputObjectType(2) = ObjType3
End If

Dim indication, n
indication = ""
For n = 0 To UBound(InputObjectType)
    indication = indication & "," & InputObjectType(n)
Next

Picked = False
NotSel = True
    Do While NotSel
        Status = S2.SelectElement2(InputObjectType, "Select the " & indication, False)
        If (Status = "Cancel") Then
            Set Sel = Nothing 'modified 20200616
            MsgBox "已退出选择", vbSystemModal
            Exit Function
        ElseIf (Status = "Redo" And Not Picked) Then
               ElseIf (Status = "Undo") Then
                        Exit Function
                    ElseIf (Status <> "Redo") Then Set obj = S2.Item2(1).Value
                              Picked = True
                              NotSel = False
        End If
    Loop
    S2.Clear
    Set Sel = obj
End Function

'##############创建字符####################################
Private Sub CreateText(txt0 As String)
If txt0 = "" Then
MsgBox "要刻字的内容为空！请输入要刻字的内容再运行！"
Exit Sub
End If

Dim NowWin
Set NowWin = CATIA.ActiveWindow
Dim settingRepository1
On Error Resume Next
Set settingRepository1 = CATIA.SettingControllers.Item("DXF")
settingRepository1.Commit '暂存当前设置
settingRepository1.PutAttr "ImportUnit", 0 'Millimeter
settingRepository1.PutAttr "ExportMode", 1 'Graphic
On Error GoTo 0
Dim TemDoc As DrawingDocument: Dim TemText As DrawingText: Dim TemTextDXF As String
TemTextDXF = oCATVBA_Folder("Temp") & "\" & Right$("0" & CStr(Minute(Now)), 2) & Right$("0" & CStr(Second(Now)), 2) & ".dxf"
Set TemDoc = CATIA.Documents.Add("Drawing")
TemDoc.Standard = catISO
Set TemText = TemDoc.Sheets.ActiveSheet.Views.ActiveView.Texts.Add(txt0, 0, 0)
TemDoc.Sheets.ActiveSheet.ForceUpdate
TemText.SetFontName 0, 0, cbxFontName.Text
TemText.SetFontSize 0, 0, CDbl(cbxFontSize.Text)
TemText.SetParameterOnSubString 15, 0, 0, Val(cbxSpacing.Text) * 100
Select Case cbxLocation.ListIndex
Case 0
TemText.AnchorPosition = 5 'catMiddleCenter
TemText.x = CoGCoordInUserAxis(0): TemText.y = CoGCoordInUserAxis(1)
Case 1
TemText.AnchorPosition = 6 'catBottomCenter
TemText.x = xCenter: TemText.y = Val(cbxY.Text)
Case 2
TemText.AnchorPosition = 3 'catBottomLeft
TemText.x = Val(cbxX.Text): TemText.y = Val(cbxY.Text)
Case Else
TemText.AnchorPosition = 3 'catBottomLeft
TemText.x = 0: TemText.y = 0
End Select
TemDoc.Sheets.ActiveSheet.ForceUpdate
Select Case cbxMirror.ListIndex
Case 0
TemText.TextProperties.Mirror = 0 ' catTextNoFlip
Case 1
TemText.TextProperties.Mirror = 1 ' catTextHorizontalFlip
Case 2
TemText.TextProperties.Mirror = 2 ' catTextVerticalFlip
Case 3
TemText.TextProperties.Mirror = 3 ' catTextHorizontalAndVerticalFlip
End Select
TemDoc.Sheets.ActiveSheet.ForceUpdate
TemDoc.Update
TemDoc.ExportData TemTextDXF, "dxf"
TemDoc.Update
TemDoc.Close
Dim TemDoc2
Set TemDoc2 = CATIA.Documents.Open(TemTextDXF)
Dim TemSlct
Set TemSlct = CATIA.ActiveDocument.Selection
TemSlct.Clear
Dim colGeometry As GeometricElements
Set colGeometry = CATIA.ActiveDocument.Sheets.ActiveSheet.Views.ActiveView.GeometricElements
Dim tempPolyline
For Each tempPolyline In colGeometry
TemSlct.Add tempPolyline
Next
TemSlct.Copy
NowWin.Activate
Dim sketch1, sketch1Variant
If tarBody Is Nothing Then
Set sketch1 = tarHybridBody.HybridSketches.Add(selPlanarFace)
Else
Set sketch1 = tarBody.Sketches.Add(selPlanarFace)
End If
Set sketch1Variant = sketch1
sketch1Variant.SetAbsoluteAxisData sketchVariantOfDouble
sketch1.OpenEdition
CATIA.ActiveDocument.Selection.Clear
CATIA.ActiveDocument.Selection.Add sketch1
CATIA.ActiveDocument.Selection.Paste
CATIA.ActiveDocument.Selection.Clear
sketch1.CloseEdition
sketch1.Name = "TextSketch_" & Right$("0" & CStr(Minute(Now)), 2) & Right$("0" & CStr(Second(Now)), 2)
tarPart.Update
TemDoc2.Close
On Error Resume Next
settingRepository1.Rollback '恢复设置
On Error GoTo 0
Kill TemTextDXF
If extrueSketch = False Then
tarPart.Update
Exit Sub
End If

Dim Tempad
On Error Resume Next
Err.Clear
If cbxFontName.ListIndex <> 3 And cbxFontName.ListIndex <> 4 Then '不是单线字体
    If Val(cbxHeight.Text) > 0 Then
    Set Tempad = tarPart.ShapeFactory.AddNewPad(sketch1, Val(cbxHeight.Text))
    Tempad.SecondLimit.LimitMode = 3 'catUpToPlaneLimit
    Tempad.SecondLimit.LimitingElement = selPlanarFace
    Tempad.Name = "TextPad"
    Else
    Set Tempad = tarPart.ShapeFactory.AddNewPocket(sketch1, Abs(Val(cbxHeight.Text)))
    Tempad.SecondLimit.LimitMode = 3 'catUpToPlaneLimit
    Tempad.SecondLimit.LimitingElement = selPlanarFace
    Tempad.Name = "TextPocket"
    End If
End If
If (cbxFontName.ListIndex = 3 Or cbxFontName.ListIndex = 4) And Val(cbxThickness.Text) > 0 Then '单线字体且加厚值不等于0
    If Val(cbxHeight.Text) > 0 Then
    Set Tempad = tarPart.ShapeFactory.AddNewPad(sketch1, Val(cbxHeight.Text))
    Tempad.SecondLimit.LimitMode = 3 'catUpToPlaneLimit
    Tempad.SecondLimit.LimitingElement = selPlanarFace
    Tempad.Name = "TextPad"
    Else
    Set Tempad = tarPart.ShapeFactory.AddNewPocket(sketch1, Abs(Val(cbxHeight.Text)))
    Tempad.SecondLimit.LimitMode = 3 'catUpToPlaneLimit
    Tempad.SecondLimit.LimitingElement = selPlanarFace
    Tempad.Name = "TextPocket"
    End If
Tempad.IsThin = True
Dim Parameters2 'As Parameters
Set Parameters2 = tarPart.Parameters.SubList(Tempad, False)
Dim par 'As Parameter
For Each par In Parameters2
    Dim mainStr, subStrCN, subStrEN, position
    'Debug.Print par.Name
    mainStr = par.Name
    subStrCN = "厚薄": subStrEN = "ThickThin"
    position = InStr(1, mainStr, subStrCN, vbTextCompare)
    If position > 0 Then
        par.Value = Val(cbxThickness.Text) / 2
    End If
    position = InStr(1, mainStr, subStrEN, vbTextCompare)
    If position > 0 Then
        par.Value = Val(cbxThickness.Text) / 2
    End If
Next
End If
tarPart.Update
If Err.Number <> 0 Then
MsgBox "无法创建拉伸或切除特征，已保留文本草图！"
CATIA.ActiveDocument.Selection.Clear
CATIA.ActiveDocument.Selection.Add Tempad
CATIA.ActiveDocument.Selection.Delete
tarPart.Update
End If
End Sub

'###########提取字符串第一个空格之前部分，为了处理字体名称##########
Private Function StringBeforeSpace(s As String) As String
s = Trim(s)
Dim spacePos As Integer
spacePos = InStr(s, " ")  '查找第一个空格的位置
If spacePos > 0 Then
    StringBeforeSpace = Left(s, spacePos - 1)  '提取空格前的部分
Else
    StringBeforeSpace = StringBeforeSpace  '如果没有空格，返回原字符串
End If
End Function

'####################保存用户设置##########################
Private Sub SaveConf()
On Error Resume Next
Dim sConfpath As String
Dim write1 'As Long
    '参数一： Section Name (节的名称)。
    '参数二： 节下面的项目名称。
    '参数三： 项目的内容。
    '参数四： ini配置文件的路径名称。
              
sConfpath = oCATVBA_Folder
write1 = WritePrivateProfileString("平面刻字", "文本输入类型", CStr(cbxInputType.ListIndex), sConfpath & "\Conf1.ini")

write1 = WritePrivateProfileString("平面刻字", "字体", CStr(cbxFontName.ListIndex), sConfpath & "\Conf1.ini")
write1 = WritePrivateProfileString("平面刻字", "字高", CStr(cbxFontSize.Text), sConfpath & "\Conf1.ini")
write1 = WritePrivateProfileString("平面刻字", "间距", CStr(cbxSpacing.Text), sConfpath & "\Conf1.ini")
write1 = WritePrivateProfileString("平面刻字", "凸起", CStr(cbxHeight.Text), sConfpath & "\Conf1.ini")
write1 = WritePrivateProfileString("平面刻字", "加厚", CStr(cbxThickness.Text), sConfpath & "\Conf1.ini")

write1 = WritePrivateProfileString("平面刻字", "布局", CStr(cbxLocation.ListIndex), sConfpath & "\Conf1.ini")
write1 = WritePrivateProfileString("平面刻字", "X", CStr(cbxX.Text), sConfpath & "\Conf1.ini")
write1 = WritePrivateProfileString("平面刻字", "Y", CStr(cbxY.Text), sConfpath & "\Conf1.ini")

write1 = WritePrivateProfileString("平面刻字", "镜像", CStr(cbxMirror.ListIndex), sConfpath & "\Conf1.ini")
End Sub

'####################读取用户设置##########################
Private Sub ReadConf()
Dim sConfpath As String
sConfpath = oCATVBA_Folder
Dim objFSO
Set objFSO = CreateObject("Scripting.FileSystemObject")
If Not objFSO.FileExists(sConfpath & "\Conf1.ini") Then
Exit Sub
End If
'---读取配置文件---
'On Error Resume Next
    Dim read_OK ' As Long
    Dim read2 As String
    read2 = String(255, 0)
    read_OK = GetPrivateProfileString("平面刻字", "文本输入类型", "0", read2, 256, sConfpath & "\Conf1.ini")
    cbxInputType.ListIndex = read2
    read2 = String(255, 0)
    read_OK = GetPrivateProfileString("平面刻字", "字体", "1", read2, 256, sConfpath & "\Conf1.ini")
    cbxFontName.ListIndex = read2
    read2 = String(255, 0)
    read_OK = GetPrivateProfileString("平面刻字", "字高", "3.5", read2, 256, sConfpath & "\Conf1.ini")
    cbxFontSize.Text = Val(read2)
    read2 = String(255, 0)
    read_OK = GetPrivateProfileString("平面刻字", "间距", "0.1", read2, 256, sConfpath & "\Conf1.ini")
    cbxSpacing.Text = read2
    read2 = String(255, 0)
    read_OK = GetPrivateProfileString("平面刻字", "凸起", "-0.3", read2, 256, sConfpath & "\Conf1.ini")
    cbxHeight.Text = read2
    read2 = String(255, 0) '因为设置了Enable，会出错
    read_OK = GetPrivateProfileString("平面刻字", "加厚", "0.3", read2, 256, sConfpath & "\Conf1.ini")
    cbxThickness.Text = Val(read2)
    
    read2 = String(255, 0)
    read_OK = GetPrivateProfileString("平面刻字", "布局", "0", read2, 256, sConfpath & "\Conf1.ini")
    cbxLocation.ListIndex = read2
    read2 = String(255, 0)
    read_OK = GetPrivateProfileString("平面刻字", "X", "0", read2, 256, sConfpath & "\Conf1.ini")
    cbxX.Text = read2
    read2 = String(255, 0)
    read_OK = GetPrivateProfileString("平面刻字", "Y", "0", read2, 256, sConfpath & "\Conf1.ini")
    cbxY.Text = read2
    
    read2 = String(255, 0)
    read_OK = GetPrivateProfileString("平面刻字", "镜像", "0", read2, 256, sConfpath & "\Conf1.ini")
    cbxMirror.ListIndex = read2
End Sub

Private Sub txtInput_Change()

End Sub

'####################窗体启动##########################
Private Sub UserForm_Activate()

    cbxInputType.AddItem "输入文本": cbxInputType.AddItem "用零件编号刻字": cbxInputType.AddItem "用几何体名称刻字"
    cbxInputType.ListIndex = 0
    cbxInputType.Style = fmStyleDropDownList
    
    cbxFontName.AddItem "DengXian (TrueType)": cbxFontName.AddItem "FangSong (TrueType)": cbxFontName.AddItem "KaiTi (TrueType)": cbxFontName.AddItem "SICH": cbxFontName.AddItem "SSS4"
    cbxFontName.ListIndex = 1
    cbxFontName.Style = fmStyleDropDownList
    
    cbxFontSize.AddItem "2.5": cbxFontSize.AddItem "3.5": cbxFontSize.AddItem "5.0": cbxFontSize.AddItem "7.0": cbxFontSize.AddItem "10.0"
    cbxFontSize.AddItem "14.0": cbxFontSize.AddItem "18.0": cbxFontSize.AddItem "20.0"
    cbxFontSize.ListIndex = 2
    
    cbxSpacing.AddItem "0": cbxSpacing.AddItem "0.1": cbxSpacing.AddItem "0.2": cbxSpacing.AddItem "0.5": cbxSpacing.AddItem "0.8": cbxSpacing.AddItem "1.0"
    cbxSpacing.ListIndex = 1
    
    cbxHeight.AddItem "-0.8": cbxHeight.AddItem "-0.5": cbxHeight.AddItem "-0.3": cbxHeight.AddItem "0": cbxHeight.AddItem "0.3"
    cbxHeight.AddItem "0.5": cbxHeight.AddItem "0.8": cbxHeight.AddItem "1.0"
    cbxHeight.ListIndex = 3
    
    cbxThickness.AddItem "0.2": cbxThickness.AddItem "0.3": cbxThickness.AddItem "0.5": cbxThickness.AddItem "0.8": cbxThickness.AddItem "1.0"
    cbxThickness.ListIndex = 1
    
    cbxLocation.AddItem "自动居中(自动判断）": cbxLocation.AddItem "X居中": cbxLocation.AddItem "XY距离"
    cbxLocation.ListIndex = 1
    cbxLocation.Style = fmStyleDropDownList
    
    cbxX.AddItem "0": cbxX.AddItem "4": cbxX.AddItem "8": cbxX.AddItem "10": cbxX.AddItem "12": cbxX.AddItem "15": cbxX.AddItem "20": cbxX.AddItem "30"
    cbxX.ListIndex = 0
    
    cbxY.AddItem "0": cbxY.AddItem "4": cbxY.AddItem "8": cbxY.AddItem "10": cbxY.AddItem "12": cbxY.AddItem "15": cbxY.AddItem "20": cbxY.AddItem "30"
    cbxY.ListIndex = 0
    
    cbxMirror.AddItem "不镜像": cbxMirror.AddItem "水平翻转": cbxMirror.AddItem "垂直翻转": cbxMirror.AddItem "水平垂直翻转"
    cbxMirror.ListIndex = 0
    cbxMirror.Style = fmStyleDropDownList

    ReadConf
    On Error Resume Next
    txtInput.Font.Name = StringBeforeSpace(cbxFontName.Text) '单线字体会报错，无法设置
    txtSpecial.Font.Name = StringBeforeSpace(cbxFontName.Text) '单线字体会报错，无法设置
    On Error GoTo 0
    txtInput.Font.Size = Val(cbxFontSize.Text) * 2.8346 + 4 '转换是1 毫米 ≈ 2.8346 磅，+4是为了界面好阅读
End Sub

Private Sub UserForm_QueryClose(Cancel As Integer, CloseMode As Integer)
SaveConf
End Sub
' 向量减法
Sub VectorSubtract(ByRef v1() As Double, ByRef v2() As Double, ByRef Result() As Double)
    Result(0) = v1(0) - v2(0)
    Result(1) = v1(1) - v2(1)
    Result(2) = v1(2) - v2(2)
End Sub

' 向量叉乘
Sub CrossProduct(ByRef v1() As Double, ByRef v2() As Double, ByRef Result() As Double)
    Result(0) = v1(1) * v2(2) - v1(2) * v2(1)
    Result(1) = v1(2) * v2(0) - v1(0) * v2(2)
    Result(2) = v1(0) * v2(1) - v1(1) * v2(0)
End Sub

' 向量点乘
Function dotProduct(ByRef v1() As Double, ByRef v2() As Double) As Double
    dotProduct = v1(0) * v2(0) + v1(1) * v2(1) + v1(2) * v2(2)
End Function

' 向量归一化
Sub NormalizeVector(ByRef v() As Double)
    Dim length As Double
    length = Sqr(v(0) * v(0) + v(1) * v(1) + v(2) * v(2))
    
    If length > 0 Then
        v(0) = v(0) / length
        v(1) = v(1) / length
        v(2) = v(2) / length
    End If
End Sub
' ############计算用户坐标系############
Sub CalculateUserCoordinateSystem( _
    ByRef A() As Double, _
    ByRef B() As Double, _
    ByRef C() As Double, _
    ByRef z() As Double, _
    ByRef vUp() As Double, _
    ByRef Cnew() As Double, _
    ByRef Origin() As Double, _
    ByRef XAxis() As Double, _
    ByRef YAxis() As Double, _
    ByRef ZAxis() As Double)
    
    ' 首先尝试以A为原点
    Dim success As Boolean
    
    ' 初始化数组
    If Not IsArray(Origin) Then ReDim Origin(2)
    If Not IsArray(XAxis) Then ReDim XAxis(2)
    If Not IsArray(YAxis) Then ReDim YAxis(2)
    If Not IsArray(ZAxis) Then ReDim ZAxis(2)
    
    success = TryCalculateSystem(A, B, C, z, vUp, Cnew, Origin, XAxis, YAxis, ZAxis)
    
    ' 如果以A为原点失败，则尝试以B为原点
    If Not success Then
        success = TryCalculateSystem(B, A, C, z, vUp, Cnew, Origin, XAxis, YAxis, ZAxis)
    End If
    
    ' 如果两次尝试都失败，抛出错误
    If Not success Then
        Err.Raise 5, "CalculateUserCoordinateSystem", "无法创建符合条件的用户坐标系"
    End If
End Sub

' ############尝试以给定的原点计算用户坐标系############
Function TryCalculateSystem( _
    ByRef Origin() As Double, _
    ByRef OtherEnd() As Double, _
    ByRef C() As Double, _
    ByRef z() As Double, _
    ByRef vUp() As Double, _
    ByRef Cnew() As Double, _
    ByRef OutOrigin() As Double, _
    ByRef OutXAxis() As Double, _
    ByRef OutYAxis() As Double, _
    ByRef OutZAxis() As Double) As Boolean
    
    ' 设置原点
    Dim i As Integer
    For i = 0 To 2
        OutOrigin(i) = Origin(i)
    Next
    
    ' 计算X轴方向（从原点到另一个端点的向量）
    Dim xDir(2) As Double
    VectorSubtract OtherEnd, Origin, xDir
    NormalizeVector xDir
    
    ' 复制X轴
    For i = 0 To 2
        OutXAxis(i) = xDir(i)
    Next
    
    ' 计算从原点到点C的向量
    Dim cDir(2) As Double
    VectorSubtract C, Origin, cDir
    
    ' 计算初始Z轴方向（X轴和C方向的叉乘）
    Dim zDir(2) As Double
    CrossProduct OutXAxis, cDir, zDir
    
    ' 检查Z轴是否有效（如果为零向量，表示三点共线）
    Dim zLength As Double
    zLength = Sqr(zDir(0) * zDir(0) + zDir(1) * zDir(1) + zDir(2) * zDir(2))
    If zLength < 0.0001 Then
        TryCalculateSystem = False
        Exit Function
    End If
    
    ' 归一化Z轴
    NormalizeVector zDir
    
    ' 检查Z轴与参考Z方向的点积（确保夹角不大于90度）
    Dim zDotProduct As Double  ' 重命名变量，避免与函数名冲突
    zDotProduct = dotProduct(zDir, z)  ' 正确调用函数，移除括号
    
    ' 如果点积为负，说明夹角大于90度，需要反转Z轴方向
    If zDotProduct < 0 Then
        For i = 0 To 2
            zDir(i) = -zDir(i)
        Next
    End If
    
    ' 复制Z轴
    For i = 0 To 2
        OutZAxis(i) = zDir(i)
    Next
    
    ' 计算Y轴方向（Z轴和X轴的叉乘，确保右手定则）
    CrossProduct OutZAxis, OutXAxis, OutYAxis
    
    '检查Y轴方向是否与 vUp方向夹角小于90度
    
      Dim yDotProduct As Double  ' 重命名变量，避免与函数名冲突
    yDotProduct = dotProduct(OutYAxis, vUp)  ' 正确调用函数，移除括号
    
    ' 如果点积为负，说明夹角大于90度，需要反转Y轴方向
    ' 如果点积为非负，说明夹角小于90度，坐标系正确
    If yDotProduct >= 0 Then
        ' 检查另一个端点在用户坐标系中的X坐标是否为正
        Dim otherEndXCoord As Double
        otherEndXCoord = dotProduct(xDir, OutXAxis)
        If otherEndXCoord > 0 Then
            TryCalculateSystem = True
            ' 计算点C在用户坐标系中的XY坐标
            Cnew(0) = dotProduct(cDir, OutXAxis): Cnew(1) = dotProduct(cDir, OutYAxis)
            Exit Function
        End If
    End If

    ' 如果不满足条件，返回失败
    TryCalculateSystem = False
End Function

'############ 判断两个单位向量是否平行（方向相同或相反）############
Function AreUnitVectorsParallel(t1() As Double, t2() As Double) As Boolean
    ' 计算点积
    Dim dotProduct1 As Double
    dotProduct1 = dotProduct(t1, t2)
    
    ' 设置一个小的容差值，处理浮点数精度问题
    Dim tolerance As Double
    tolerance = 0.000001
    
    ' 如果点积的绝对值接近1，则认为向量平行
    AreUnitVectorsParallel = (Abs(Abs(dotProduct1) - 1) < tolerance)
End Function

Attribute VB_Name = "TextOnPlanarFace_3D"
Sub CATMain()
    On Error Resume Next
    
    ' 1. 獲取微軟核心組件（自動相容 32/64 位 CATIA）
    Dim oApc As Object
    #If VBA7 Then
        Set oApc = CreateObject("MSAPC.Apc.7.1")
    #Else
        Set oApc = CreateObject("MSAPC.Apc.6.2")
    #End If
    
    ' 2. 動態抓取目前正在運行的 .catvba 專案檔完整路徑
    Dim sProjectPath As String
    sProjectPath = oApc.ExecutingProject.DisplayName
    
    ' 3. 初始化檔案系統物件
    Dim fso As Object
    Set fso = CreateObject("Scripting.FileSystemObject")
    
    ' 4. 【注意】：這裡去掉了原本的 "Dim"，直接對全域變數進行賦值
    If fso.FileExists(sProjectPath) Then
        Set oCATVBA_Folder = fso.GetFolder(fso.GetParentFolderName(sProjectPath))
    Else
        Set oCATVBA_Folder = fso.GetFolder(fso.GetParentFolderName(CATIA.ActiveDocument.FullName))
    End If
    MsgBox (oCATVBA_Folder)
    On Error GoTo 0

TextOnPlanarFace.Show vbModeless
TextOnPlanarFace.Left = TextOnPlanarFace.Left * 2
End Sub
